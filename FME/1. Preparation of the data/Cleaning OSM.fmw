FME workspace Cleaning OSM.fmw

Parameters:
- DestDataset_SHAPEFILE =
- DestDataset_SHAPEFILE_5 =
- DestDataset_SHAPEFILE_6 =
- SourceDataset_SHAPEFILE =
- bbox_crs =
- max_x =
- max_y =
- min_x =
- min_y =

Readers:
- SHAPEFILE_1: SHAPEFILE from $(SourceDataset_SHAPEFILE)

Writers:
- SHAPEFILE_2: SHAPEFILE to $(DestDataset_SHAPEFILE)
- SHAPEFILE_3: SHAPEFILE to $(DestDataset_SHAPEFILE_5)
- SHAPEFILE_4: SHAPEFILE to $(DestDataset_SHAPEFILE_6)

Bookmark: Get road features from OpenStreetMap overpass API
Creator_2
    GEOMTYPE = Geometry Object
    NUM = 1
    CREATED -> AttributeManager_3
AttributeManager_3
    ATTR_TABLE:
      REMOVE _creation_instance
      SET_TO max_x = $(max_x)
      SET_TO max_y = $(max_y)
      SET_TO min_x = $(min_x)
      SET_TO min_y = $(min_y)
    -> AttributeReprojector
AttributeReprojector
    DEST = EPSG:4326
    SOURCE = EPSG:31370
    XATTR = max_x
    YATTR = max_y
    -> AttributeReprojector_2
AttributeReprojector_2
    DEST = EPSG:4326
    SOURCE = EPSG:31370
    XATTR = min_x
    YATTR = min_y
    -> HTTPCaller
Note: HTTPCaller / OSM overpass API
HTTPCaller
    ADDITIONAL_URL_PARAMETERS:
      data;[out:xml];
      (
        way["unknown"=""](@Value(min_y),@Value(min_x),@Value(max_y),@Value(max_x));
      );
      out body;
      >;
      out skel qt;
    CONNECTION_TIMEOUT_LENGTH = 60
    ERROR_ATTR = _error
    FILE_PATH_ATTR = _response_file_path
    FOLLOW_REDIRECTS = Yes
    HTTP_METHOD = GET
    OUTPUT_FILENAME = ./output/osm.xml
    SAVE_FILE = File
    SAVE_MULTI = No
    STATUS_CODE_ATTR = _http_status_code
    TARGET_URL = http://overpass-api.de/api/interpreter
    TRANSFER_TIMEOUT_LENGTH = 90
    USE_COOKIES = No
    VERIFY_SSL_CERTIFICATES = Yes
    -> FeatureReader [INITIATOR]
FeatureReader
    ATTRIBUTES = aerialway,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,source,aerialway",aeroway,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,building,ele,surface,ref,source,aeroway",amenity,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,shelter,ref,ele,gnis:feature_id,gnis:created,gnis:county_id,gnis:state_id,atm,backrest,recycling_type,recycling:glass,support,covered,bicycle_parking,network,brand,religion,wheelchair,operator:type,addr:housenumber,shelter_type,vending,sport,note,parking,access,capacity,cuisine,addr:street,social_facility,source,operator,building,amenity",barrier,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,source,historic,landuse,stile,foot,bicycle,name,barrier",boundary,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,admin_level,source,name,protect_class,protection_title,leisure,attribution,note,type,postal_code,boundary",building,"fme_geometry{0},fme_geometry{1},fme_geometry{2},fme_geometry{3},fme_geometry{4},id,timestamp,user,visible,created_by,area,uid,version,changeset,tag{}.k,tag{}.v,nd{}.ref,member{}.type,member{}.ref,member{}.role,osm_feature_type,osm_theme,source,military,denomination,ref:ruian:building,building:ruian:type,construction,fixme,tourism,ref:bag,source:date,religion,amenity,start_date,layer,building:use:pl,addr:housenumber,addr:city,addr:postcode,power,substation,building:usage:pl,building:levels,name,addr:street,height,building",craft,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,addr:street,addr:housenumber,craft",emergency,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,fire_hydrant:type,fire_hydrant:diameter,fire_hydrant:position,access,operator,highway,name,foot,emergency",geological,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,natural,type,geological",highway,"fme_geometry{0},fme_geometry{1},fme_geometry{2},fme_geometry{3},fme_geometry{4},id,timestamp,user,visible,created_by,layer,uid,version,changeset,tag{}.k,tag{}.v,nd{}.ref,member{}.type,member{}.ref,member{}.role,osm_feature_type,osm_theme,name,maxspeed,service,proposed,crossing,construction,sport,bicycle,foot,level,wheelchair,distance,surface,public_transport,bus,lanes,tiger:cfcc,area,ref,incline,direction,tracktype,oneway,source,highway",historic,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,site_type,ref,building,source,religion,historic",landuse,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,source,massgis:PUB_ACCESS,ownership,owner,leisure,protected,massgis:TOWN_ID,massgis:FEE_OWNER,massgis:ARTICLE97,natural,water,building,source:date,logging:start_date,type,barrier,name,landuse",leisure,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,sport,source,type,access,addr:street,website,boundary,building,name,leisure",man_made,"fme_geometry{0},fme_geometry{1},fme_geometry{2},fme_geometry{3},fme_geometry{4},id,timestamp,user,visible,created_by,area,uid,version,changeset,tag{}.k,tag{}.v,nd{}.ref,member{}.type,member{}.ref,member{}.role,osm_feature_type,osm_theme,source,surveillance,surveillance:type,street_cabinet,operator,location,type,layer,tower:type,communication:mobile_phone,building,note,ref,ele,name,man_made",military,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,building,bunker_type,historic,military",natural,"fme_geometry{0},fme_geometry{1},fme_geometry{2},fme_geometry{3},fme_geometry{4},id,timestamp,user,visible,created_by,layer,uid,version,changeset,tag{}.k,tag{}.v,nd{}.ref,member{}.type,member{}.ref,member{}.role,osm_feature_type,osm_theme,source,wetland,golf,area,attribution,type,nhd:com_id,nhd:fdate,ele,mountain_pass,source_ref,LINZ:dataset,LINZ:layer,LINZ:source_version,name,natural",office,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,addr:street,building,addr:housenumber,office",place,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,source,is_in:state_code,is_in:state,wikidata,is_in:country,is_in:country_code,name:en,wikipedia,is_in,landuse,natural,place",power,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,source,ref,location,frequency,generator:source,generator:method,generator:output:electricity,cables,name,substation,building,operator,voltage,power",public_transport,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,bus,highway,network,type,railway,operator,public_transport",railway,"fme_geometry{0},fme_geometry{1},fme_geometry{2},fme_geometry{3},fme_geometry{4},id,timestamp,user,visible,created_by,layer,uid,version,changeset,tag{}.k,tag{}.v,nd{}.ref,member{}.type,member{}.ref,member{}.role,osm_feature_type,osm_theme,gauge,electrified,wheelchair,railway:signal:direction,railway:signal:position,tram,highway,crossing,railway:position,railway:milestone:catenary_mast,area,service,wikipedia,name,public_transport,train,voltage,frequency,ref,railway",route,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,network,type,name,ref,operator,osmc:symbol,foot,note,highway,voltage,cables,wires,frequency,route",shop,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,addr:street,source,building,addr:housenumber,shop",sport,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,leisure,name,golf,landuse,natural,surface,sport",tourism,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,name,information,ele,artwork_type,addr:street,building,tourism",unfiltered,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,unfiltered",unknown,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,unknown",waterway,"fme_geometry{0},fme_geometry{1},fme_geometry{2},fme_geometry{3},fme_geometry{4},id,timestamp,user,visible,created_by,area,layer,uid,version,changeset,tag{}.k,tag{}.v,nd{}.ref,member{}.type,member{}.ref,member{}.role,osm_feature_type,osm_theme,source,gnis:feature_id,ele,tunnel,name,waterway"
    ATTR_ACCUM_MODE = Only Use Result
    COMBINE_GEOM = Use Result
    DATASET = ./output/osm.xml
    FEATURETYPES = barrier aerialway aeroway amenity boundary highway man_made public_transport railway route unfiltered unknown waterway
    FORMAT = OSM
    INTERACT = <No Spatial Filter>
    OSM_ALLOW_DUPLICATE_COORDINATES = no
    OSM_BUILD_MULTIPOLYGON_RELATION = yes
    OSM_CACHE_WAYS_AND_RELATIONS = no
    OSM_COMMUNITY_FEATURE_TYPES = MAPPED
    OSM_HANDLE_MULTI = SELECT_FIRST
    OSM_OUTPUT_INCOMPLETE_WAYS_AND_RELATIONS = yes
    OSM_REMOVE_NODE_LIST = yes
    OSM_SCAN_ALL_FEATURES_FOR_SCHEMA = no
    OSM_USER_CONFIG = NO
    OSM_USE_SEARCH_ENVELOPE = NO
    OUTPUT_FEATURES_DISPLAY = Data Features
    highway -> Reprojector
Reprojector
    DEST = $(bbox_crs)
    INTERPOLATION_TYPE_NAME = Nearest Neighbor
    RASTER_CELL_SIZE = Preserve Cells
    RASTER_TOLERANCE = 0.0
    SOURCE = Read from feature
    REPROJECTED -> Clipper_11 [CLIPPEE]
UrbAdm_REGION (reader SHAPEFILE_1)
    attributes: ID long, VERSIONID long, NAME_FRE varchar(60), NAME_DUT varchar(60), COUNTRY varchar(2), NAT_CODE varchar(15), NAT_LEVEL short, AREA double, LEGAL_STAT varchar(20), INSPIRE_ID varchar(50), BEGIN_LIFE date, END_LIFE date
    -> Clipper_11 [CLIPPER]
Clipper_11
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> GeometryValidator
GeometryValidator
    ISSUE_ATTR_NAME = _issues
    PRESETS = Custom
    REPAIR = Yes
    RULES = AREA_ORIENTATION AREA_ORIENTATION]VALID]FME_CONTROLLER_QUERY_FILE]transformers/dependencies/geometryvalidator/AREA_ORIENTATION.fme CONSECUTIVE_IDENTICAL_VERTICES_2D CHECK_Z]YES]FME_CONTROLLER_QUERY_FILE]transformers/dependencies/geometryvalidator/CONSECUTIVE_IDENTICAL_VERTICES_2D.fme MISSING_TEXTURE_COORDINATES FME_CONTROLLER_QUERY_FILE]transformers/dependencies/geometryvalidator/MISSING_TEXTURE_COORDINATES.fme]FME_CONTROLLER_CHOICE]MISSING_TEXTURE_COORDINATES MISSING_VERTEX_NORMALS FME_CONTROLLER_QUERY_FILE]transformers/dependencies/geometryvalidator/MISSING_VERTEX_NORMALS.fme]FME_CONTROLLER_CHOICE]MISSING_VERTEX_NORMALS NAN_REMOVAL PROCESS_MEASURE]NO]FME_CONTROLLER_QUERY_FILE]transformers/dependencies/geometryvalidator/NAN_REMOVAL.fme NULL_REMOVAL FME_CONTROLLER_QUERY_FILE]transformers/dependencies/geometryvalidator/NULL_REMOVAL.fme]FME_CONTROLLER_CHOICE]NULL_REMOVAL PLANAR_SURFACE CHECK_AREA]DO_NOT_CHECK_AREA]TOLERANCE_MODE]AUTO]TOLERANCE]0.0]ANGULAR_TOLERANCE_MODE]AUTO]ANGULAR_TOLERANCE]0.0]FME_CONTROLLER_QUERY_FILE]transformers/dependencies/geometryvalidator/PLANAR_SURFACE.fme SELF_INTERSECTING CHECK_HOLE_TOUCHING_POLYGON]No]CONNECT_Z_MODE_SI]FIRST_WINS]SELF_INTERSECTION_TOLERANCE]None]FME_CONTROLLER_QUERY_FILE]transformers/dependencies/geometryvalidator/SELF_INTERSECTING.fme SHELL_VALIDATION FLIP_APPEARANCE_MODE]FLIP_APPEARANCES]FME_CONTROLLER_QUERY_FILE]transformers/dependencies/geometryvalidator/SHELL_VALIDATION.fme SOLID_VOID_REPAIR FME_CONTROLLER_QUERY_FILE]transformers/dependencies/geometryvalidator/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]0.0]FME_CONTROLLER_QUERY_FILE]transformers/dependencies/geometryvalidator/TYPE_REPAIR.fme MISMATCHED_DIMENSIONS FORCE_DIMENSION]2D]FME_CONTROLLER_QUERY_FILE]transformers/dependencies/geometryvalidator/MISMATCHED_DIMENSIONS.fme MISSING_MEASURES_AND_ELEVATIONS MISSING_VALUES_MODE]SENTINEL]SENTINEL_VALUE]0]MISSING_MEASURES_MODE]CONTINUOUS]LENGTH_DIMENSION]2D]FME_CONTROLLER_QUERY_FILE]transformers/dependencies/geometryvalidator/MISSING_MEASURES_AND_ELEVATIONS.fme SURFACE_ORIENTATION FME_CONTROLLER_QUERY_FILE]transformers/dependencies/geometryvalidator/SURFACE_ORIENTATION.fme]FME_CONTROLLER_CHOICE]SURFACE_ORIENTATION SOLID_ORIENTATION FME_CONTROLLER_QUERY_FILE]transformers/dependencies/geometryvalidator/SOLID_ORIENTATION.fme]FME_CONTROLLER_CHOICE]SOLID_ORIENTATION
    SUMMARY = Detailed
    PASSED -> TestFilter
    PASSED -> TestFilter_2
    REPAIRED -> TestFilter
    REPAIRED -> TestFilter_2
TestFilter
    DEFAULT_VALUE = <UNFILTERED>
    TEST_LIST:
      "BOOL_OP,OR,COMPOSITE_TEST,""""""1 OR 2 OR 3 OR 4 OR 5 OR 6 OR 7 OR 8 OR 9 OR 10 OR 11 OR 12 OR 13 OR 14 OR 15 OR 16 OR 17 OR 18 OR 19 OR 20"""""",TEST_CLAUSE,TEST @Value(highway) = bridleway
      TEST @Value(highway) = corridor
      TEST @Value(highway) = crossing
      TEST @Value(highway) = elevator
      TEST @Value(highway) = footway
      TEST @Value(highway) = cycleway
      TEST @Value(highway) = living_street
      TEST @Value(highway) = path
      TEST @Value(highway) = pedestrian
      TEST @Value(highway) = platform
      TEST @Value(highway) = primary
      TEST @Value(highway) = primary_link
      TEST @Value(highway) = residential
      TEST @Value(highway) = secondary
      TEST @Value(highway) = secondary_link
      TEST @Value(highway) = steps
      TEST @Value(highway) = tertiary
      TEST @Value(highway) = tertiary_link
      TEST @Value(highway) = track
      TEST @Value(highway) = unclassified",Foot
    Foot -> LengthCalculator
LengthCalculator
    DIM = 2
    LEN_ATTR = LENGTH
    MULT = 1
    -> Foot (writer SHAPEFILE_3)
Foot (writer SHAPEFILE_3)
    attributes: fme_geomet varchar(200), fme_geom00 varchar(200), fme_geom01 varchar(200), fme_geom02 varchar(200), fme_geom03 varchar(200), id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), maxspeed varchar(254), service varchar(254), proposed varchar(254), crossing varchar(254), constructi varchar(254), sport varchar(254), bicycle varchar(254),
      foot varchar(254), level varchar(254), wheelchair varchar(254), distance varchar(254), surface varchar(254), public_tra varchar(254), bus varchar(254), lanes varchar(254), tiger:cfcc varchar(254), area varchar(254), ref varchar(254), incline varchar(254), direction varchar(254), tracktype varchar(254), oneway varchar(254), source varchar(254), highway varchar(254), _clipped varchar(3), _issues___ varchar(200), _issues_00 varchar(200), _issues_01 varchar(200), _issues_02 varchar(200), _issues_03 varchar(200), LENGTH double
TestFilter_2
    DEFAULT_VALUE = <UNFILTERED>
    TEST_LIST:
      "BOOL_OP,OR,COMPOSITE_TEST,""""""1 OR 2 OR 3 OR 4 OR 5 OR 6 OR 7 OR 8 OR 9 OR 10 OR 11 OR 12 OR 13 OR 14 OR 15"""""",TEST_CLAUSE,TEST @Value(highway) = crossing
      TEST @Value(highway) = footway
      TEST @Value(highway) = cycleway
      TEST @Value(highway) = living_street
      TEST @Value(highway) = path
      TEST @Value(highway) = pedestrian
      TEST @Value(highway) = primary
      TEST @Value(highway) = primary_link
      TEST @Value(highway) = residential
      TEST @Value(highway) = secondary
      TEST @Value(highway) = secondary_link
      TEST @Value(highway) = tertiary
      TEST @Value(highway) = tertiary_link
      TEST @Value(highway) = track
      TEST @Value(highway) = unclassified",Bike
    Bike -> LengthCalculator_2
LengthCalculator_2
    DIM = 2
    LEN_ATTR = LENGTH
    MULT = 1
    -> Bike (writer SHAPEFILE_4)
Bike (writer SHAPEFILE_4)
    attributes: fme_geomet varchar(200), fme_geom00 varchar(200), fme_geom01 varchar(200), fme_geom02 varchar(200), fme_geom03 varchar(200), id varchar(254), timestamp varchar(254), user varchar(254), visible varchar(254), created_by varchar(254), layer varchar(254), uid varchar(254), version varchar(254), changeset varchar(254), tag___k varchar(254), tag___v varchar(254), nd___ref varchar(254), member___t varchar(254), member___r varchar(254), member__00 varchar(254), osm_featur varchar(254), osm_theme varchar(254), name varchar(254), maxspeed varchar(254), service varchar(254), proposed varchar(254), crossing varchar(254), constructi varchar(254), sport varchar(254), bicycle varchar(254),
      foot varchar(254), level varchar(254), wheelchair varchar(254), distance varchar(254), surface varchar(254), public_tra varchar(254), bus varchar(254), lanes varchar(254), tiger:cfcc varchar(254), area varchar(254), ref varchar(254), incline varchar(254), direction varchar(254), tracktype varchar(254), oneway varchar(254), source varchar(254), highway varchar(254), _clipped varchar(3), _issues___ varchar(200), _issues_00 varchar(200), _issues_01 varchar(200), _issues_02 varchar(200), _issues_03 varchar(200), LENGTH double
