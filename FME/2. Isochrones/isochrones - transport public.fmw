FME workspace isochrones - transport public.fmw

Parameters:
- DestDataset_SHAPEFILE =
- DestDataset_SHAPEFILE_3 =
- DestDataset_SHAPEFILE_4 =
- DestDataset_SHAPEFILE_5 =
- DestDataset_SHAPEFILE_6 =
- DestDataset_SHAPEFILE_7 =
- Numéro =
- STIB_Bus =
- STOP_times =
- SourceDataset_SHAPEFILE =
- SourceDataset_SHAPEFILE_27 =
- SourceDataset_SHAPEFILE_28 =
- SourceDataset_SHAPEFILE_29 =
- SourceDataset_SHAPEFILE_30 =
- SourceDataset_SHAPEFILE_31 =
- SourceDataset_SHAPEFILE_32 =
- SourceDataset_SHAPEFILE_33 =
- SourceDataset_SHAPEFILE_34 =
- SourceDataset_SHAPEFILE_35 =
- SourceDataset_SHAPEFILE_36 =
- SourceDataset_SHAPEFILE_37 =
- SourceDataset_SHAPEFILE_38 =
- SourceDataset_SHAPEFILE_39 =
- SourceDataset_SHAPEFILE_40 =
- SourceDataset_SHAPEFILE_41 =
- SourceDataset_SHAPEFILE_42 =
- SourceDataset_SHAPEFILE_43 =
- SourceDataset_SHAPEFILE_44 =
- SourceDataset_SHAPEFILE_45 =
- SourceDataset_SHAPEFILE_46 =
- SourceDataset_SHAPEFILE_47 =
- SourceDataset_SHAPEFILE_48 =
- SourceDataset_SHAPEFILE_49 =
- SourceDataset_SHAPEFILE_50 =
- SourceDataset_SHAPEFILE_51 =
- destination =
- minutes =
- mode =
- réseau_routier =
- scenario =
- soustheme =
- theme =
- variable =

Readers:
- SHAPEFILE_1: SHAPEFILE from $(SourceDataset_SHAPEFILE)
- SHAPEFILE_2: SHAPEFILE from $(SourceDataset_SHAPEFILE_27)
- SHAPEFILE_3: SHAPEFILE from $(SourceDataset_SHAPEFILE_35)
- SHAPEFILE_4: SHAPEFILE from $(SourceDataset_SHAPEFILE_47)
- SHAPEFILE_5: SHAPEFILE from $(SourceDataset_SHAPEFILE_43)
- SHAPEFILE_6: SHAPEFILE from $(SourceDataset_SHAPEFILE_31)
- SHAPEFILE_7: SHAPEFILE from $(SourceDataset_SHAPEFILE_39)
- SHAPEFILE_8: SHAPEFILE from $(SourceDataset_SHAPEFILE_28)
- SHAPEFILE_9: SHAPEFILE from $(SourceDataset_SHAPEFILE_51)
- SHAPEFILE_10: SHAPEFILE from $(SourceDataset_SHAPEFILE_33)
- SHAPEFILE_11: SHAPEFILE from $(SourceDataset_SHAPEFILE_37)
- SHAPEFILE_12: SHAPEFILE from $(SourceDataset_SHAPEFILE_41)
- SHAPEFILE_13: SHAPEFILE from $(SourceDataset_SHAPEFILE_45)
- SHAPEFILE_14: SHAPEFILE from $(SourceDataset_SHAPEFILE_29)
- SHAPEFILE_15: SHAPEFILE from $(SourceDataset_SHAPEFILE_49)
- SHAPEFILE_16: SHAPEFILE from $(SourceDataset_SHAPEFILE_30)
- SHAPEFILE_17: SHAPEFILE from $(SourceDataset_SHAPEFILE_32)
- SHAPEFILE_18: SHAPEFILE from $(SourceDataset_SHAPEFILE_34)
- SHAPEFILE_19: SHAPEFILE from $(SourceDataset_SHAPEFILE_36)
- SHAPEFILE_20: SHAPEFILE from $(SourceDataset_SHAPEFILE_38)
- SHAPEFILE_21: SHAPEFILE from $(SourceDataset_SHAPEFILE_40)
- SHAPEFILE_22: SHAPEFILE from $(SourceDataset_SHAPEFILE_42)
- SHAPEFILE_23: SHAPEFILE from $(SourceDataset_SHAPEFILE_44)
- SHAPEFILE_24: SHAPEFILE from $(SourceDataset_SHAPEFILE_46)
- SHAPEFILE_25: SHAPEFILE from $(SourceDataset_SHAPEFILE_48)
- SHAPEFILE_26: SHAPEFILE from $(SourceDataset_SHAPEFILE_50)

Writers:
- SHAPEFILE_27: SHAPEFILE to $(DestDataset_SHAPEFILE)
- SHAPEFILE_28: SHAPEFILE to $(DestDataset_SHAPEFILE_3)
- SHAPEFILE_29: SHAPEFILE to $(DestDataset_SHAPEFILE_4)
- SHAPEFILE_30: SHAPEFILE to $(DestDataset_SHAPEFILE_5)
- SHAPEFILE_31: SHAPEFILE to $(DestDataset_SHAPEFILE_6)
- SHAPEFILE_32: SHAPEFILE to $(DestDataset_SHAPEFILE_7)

Note: User parameters: / "mode": TP / "theme": mobilite / economie / environnement / vivre ensemble / "soustheme": transport / partage / stationnement velo / commerces alimentaires / commerces non-alimentaires / espace public / recyclage / espace vert / petite enfance / jeunesse / senior / sport / culture / cohesion sociale / sante / "scenario": 2021 / 2024 / 2040

Bookmark: Mode: transport public +Thème +Sous-thème + Scénario
Creator_8
    GEOMTYPE = Geometry Object
    NUM = 1
    CREATED -> AttributeCreator_8
AttributeCreator_8
    ATTR_TABLE:
      SET_TO mode = $(mode)
      SET_TO theme = $(theme)
      SET_TO soustheme = $(soustheme)
      SET_TO scenario = $(scenario)
    -> RCaller_2 [Output_2]

Bookmark: Variables
Creator_9
    GEOMTYPE = Geometry Object
    NUM = 1
    CREATED -> AttributeCreator_9
AttributeCreator_9
    ATTR_TABLE = SET_TO variable = $(variable)
    -> AttributeSplitter_2
AttributeSplitter_2
    ATTR_NAME = variable
    DELIMITER = ,
    DROP_EMPTY_PARTS = No
    LIST_NAME = _list
    TRIM_OPTION = Both
    -> ListExploder_2
ListExploder_2
    ATTR_ACCUM_MODE = Merge List Attributes
    ATTR_CONFLICT_RES = Use List Attribute Values
    INDEX_ATTR = _element_index
    LIST_ATTR = _list{}
    ELEMENTS -> StringReplacer_6
StringReplacer_6
    CASE = NO
    FIND_TEXT = \
    NO_MATCH = _FME_NO_OP_
    REGEXP = NO
    REPLACE_TEXT = /
    SRC_ATTRS = variable,_list
    -> RCaller_2 [Output00]

Bookmark: Réseau routier + STIB Bus + horaire
Creator_10
    GEOMTYPE = Geometry Object
    NUM = 1
    CREATED -> AttributeCreator_10
AttributeCreator_10
    ATTR_TABLE:
      SET_TO réseau_routier = $(réseau_routier)
      SET_TO STIB_Bus = $(STIB_Bus)
      SET_TO STOP_times = $(STOP_times)
    -> StringReplacer_7
StringReplacer_7
    CASE = NO
    FIND_TEXT = \
    NO_MATCH = _FME_NO_OP_
    REGEXP = NO
    REPLACE_TEXT = /
    SRC_ATTRS = réseau_routier
    -> RCaller_2 [Output01]

Bookmark: Fichier de destination
Creator_11
    GEOMTYPE = Geometry Object
    NUM = 1
    CREATED -> AttributeCreator_11
AttributeCreator_11
    ATTR_TABLE = SET_TO destination = $(destination)
    -> StringReplacer_8
StringReplacer_8
    CASE = NO
    FIND_TEXT = \
    NO_MATCH = _FME_NO_OP_
    REGEXP = NO
    REPLACE_TEXT = /
    SRC_ATTRS = destination
    -> RCaller_2 [Output02]

Bookmark: Seuil de temps (minutes)
Creator_12
    GEOMTYPE = Geometry Object
    NUM = 1
    CREATED -> AttributeCreator_12
AttributeCreator_12
    ATTR_TABLE = SET_TO minutes = $(minutes)
    -> RCaller_2 [Output03]

Bookmark: 1. Données de points
Note: 2021
Note: 2024
Note: 2040
Note: Urbis vs OSM vs NGI ? pour l'instant Urbis / Des erreurs dans le réseau routier!
Creator_2
    GEOMTYPE = Geometry Object
    NUM = 1
    CREATED -> AttributeCreator_2
AttributeCreator_2
    ATTR_TABLE = SET_TO numero = $(Numéro)
    -> RCaller_2 [Output]
RCaller_2
    OUTPUT_SCHEMA = time cost.level modus X Y L1 L2 test lim
    QUERY_DEF:
      Output,########################################################################################
      ############################### Calculation of isochrones ##############################
      ########################################################################################

      #cpprouting method to calculate isochrones

      #More information:
      #https://cran.r-project.org/web/packages/cppRouting/cppRouting.pdf
      #https://github.com/vlarmet/cppRouting/blob/master/README.md#compute-isochrones
      #https://r-spatial.org/r/2019/09/26/spatial-networks.html

      #set the number of digits
      options(digits = 15)

      #installation of packages
      #installation of packages
      if(!"remotes" %in% installed.packages()) {
        install.packages("remotes")
      }

      cran_pkgs = c(
        "sf",
        "maptools",
        "tidyverse",
        "foreach",
        "chron",
        "tibbletime",
        "dplyr",
        "data.table",
        "cppRouting",
        "concaveman",
        "ggmap",
        "tmap",
        "microbenchmark",
        "reshape2",
        "sp",
        "rgdal",
        "tidygraph",
        "igraph",
        "tibble",
        "units",
        "osmdata",
        "rgrass7",
        "link2GI",
        "nabor",
        "ggplot2",
        "lwgeom",
        "magritrr"
      )

      library(sf)
      library(maptools)
      library(tidyverse)
      library(foreach)
      library(chron)
      library(tibbletime)
      library(dplyr)
      library(data.table)
      library(cppRouting)
      library(concaveman)
      library(ggmap)
      library(tmap)
      library(microbenchmark)
      library(reshape2)
      library(sp)
      library(rgdal)
      library(tidygraph)
      library(igraph)
      library(tibble)
      library(units)
      library(osmdata)
      library(rgrass7)
      library(link2GI)
      library(nabor)

      #preparation of the data based on user parameters

      selection1 <- Output_2$mode
      selection2 <- Output00$X_list
      selection3 <- Output01$réseau_routier
      selection4 <- Output02$destination
      selection5 <- Output03$minutes
      selection6 <- Output_2$theme
      selection7 <- Output_2$soustheme
      selection8 <- Output_2$scenario
      selection9 <- Output01$STOP_times
      selection10 <- Output01$STIB_Bus
      selection11 <- Output$numero


      #read shapefile data
      #based on file path provided as user parameter for 'reseau_routier', 'STOP_times', 'STIB_Bus', 'variable'
      stops <- read.table(file.path(selection9[1]), header = T, sep = ",")
      piscines <- st_read(file.path(selection2[1]))
      stib_bus <- st_read(file.path(selection10[1]))
      roads <- st_read(file.path(selection3[1]))

      #Prepare stop_times.txt data
      arrival_time <- chron(times= stops$arrival_time)
      times <- as.data.frame(arrival_time)
      stops_subset <- subset(stops, select = c(trip_id, stop_id, stop_sequence))
      stops_times <- cbind.data.frame(stops_subset, times)

      #Add stop_times table to stib_bus shapefile
      stib_bus_times <- merge(stib_bus, stops_times, by = "stop_id")

      #Filter out afternoon trips
      stib_bus_times_filter <- filter(stib_bus_times, arrival_time >= "14:00:00", arrival_time <= "19:00:00")

      #Remove duplicate stop_id
      stib_bus_times_unique <- stib_bus_times_filter[!duplicated(stib_bus_times_filter$stop_id),]

      #Add ID number to piscines
      piscines <- piscines %>% mutate(Id = row_number())

      ###################
      ##For all piscines
      ###################


      m=selection11[1]
      datalist3 = list()
      #for(m in 1:nrow(piscines)){

        #Buffer distance around piscine
        l = 500

        #Isolate the row as the origin point:
        row_interest <- filter(piscines, row_number()== m)

        Id <- row_interest$Id
        Id <- as.data.frame(Id)
        #Name <- row_interest$name
        #Name_piscine <- as.data.frame(Name)

        #Create the buffer:
        buffer <- row_interest %>% st_buffer(dist = l)
        st_crs(buffer) <- st_crs("+init=epsg:31370")
        st_crs(stib_bus_times_unique) <- st_crs("+init=epsg:31370")

                    #st_write(buffer, dsn ="J:/SET-SADL_User-DI0222/Projecten/Brussel-10-min/04 Model/Processing/Isochrones_R", layer = "Piscine triton buffer", driver = "ESRI Shapefile", append = F, overwrite=T)


        #Extract the row numbers of the neighbors
        comps_idx <- st_intersects(buffer, stib_bus_times_unique)[[1]]
        comps_idx <- as.data.frame(comps_idx)

         #Remove piscines for which there is no overlap between buffer and any bus stop
        #if (dim(comps_idx)[1] == 0) {
        #next
        #}

        comps_idx <- as.integer(as.character(comps_idx$comps_idx))


        #Get all the neighbors:
        comps <- stib_bus_times_unique %>% filter(row_number() %in% comps_idx)
        comps <- comps %>% mutate(Id = row_number())

                  #############################################################################################################################################################################################
                  #Calculation walking time between piscine and bus stops within buffer around piscine
                  ####################################################################################

                  options(digits = 15)

                  #Project piscine and bus stops onto the street network
                  location1 <- row_interest
                  location2 <- comps
                  urbis <- roads
                  st_crs(urbis) <- st_crs("+init=epsg:31370")
                  st_crs(location1) <- st_crs("+init=epsg:31370")
                  st_crs(location2) <- st_crs("+init=epsg:31370")

                  library("maptools")
                  location1_sp <- as(location1, 'Spatial')
                  location1_sp <- SpatialPoints(location1_sp)
                  location2_sp <- as(location2, 'Spatial')
                  location2_sp <- SpatialPoints(location2_sp)
                  urbis_sp <- as(urbis, 'Spatial')
                  snap1 <- snapPointsToLines(location1_sp,urbis_sp)
                  snap1 <- as.data.frame(snap1)
                  snap2 <- snapPointsToLines(location2_sp,urbis_sp)
                  snap2 <- as.data.frame(snap2)
                  snap2 <- snap2 %>% mutate(Id = row_number())
                  snap2_merged <- merge(snap2, comps, by = "Id")

                  #Split the street network where piscine and bus stops project onto network
                  library("lwgeom")
                  test3 <- st_as_sf(snap1,coords = c("X", "Y"))
                  on_line_all = st_cast(test3, "POINT")
                  buf_all <- st_combine(st_buffer(on_line_all,0.0000000001))
                  parts_all = st_collection_extract(lwgeom::st_split(urbis$geometry, buf_all),"LINESTRING")

                  parts_all = st_as_sf(
                      data.frame(
                      id = 1:length(parts_all),
                      geometry = parts_all
                      )
                  )

                  parts_all$length <- st_length(parts_all)

                  urbis <- parts_all

                  library("lwgeom")
                  test4 <- st_as_sf(snap2,coords = c("X", "Y"))
                  on_line_all = st_cast(test4, "POINT")
                  buf_all <- st_combine(st_buffer(on_line_all,0.0000000001))
                  parts_all = st_collection_extract(lwgeom::st_split(urbis$geometry, buf_all),"LINESTRING")

                  parts_all = st_as_sf(
                      data.frame(
                      id = 1:length(parts_all),
                      geometry = parts_all
                      )
                  )

                  parts_all$length <- st_length(parts_all)

                  urbis <- parts_all

                  #give each edge a unique index
                  edges <- urbis %>%
                  mutate(edgeID = c(1:n()))

                  #create nodes at the start and end point of each edge
                  nodes <- edges %>%
                  st_coordinates() %>%
                  as_tibble() %>%
                  mutate(edgeID = L1) %>%
                  group_by(edgeID) %>%
                  slice(c(1, n())) %>%
                  ungroup() %>%
                  mutate(start_end = rep(c('start', 'end'), times = n()/2))

                  #give each node a unique index
                  library(tidyverse)
                  nodes <- nodes %>%
                  mutate(xy = paste(.$X, .$Y)) %>%
                  group_by(X, Y) %>%
                  mutate(nodeID =cur_group_id()) %>%
                  #mutate(nodeID = group_indices(., factor(xy, levels = unique(xy)))) %>%
                  select(-xy)

                  #combine the node indices with the edges
                  source_nodes <- nodes %>%
                  filter(start_end == 'start') %>%
                  pull(nodeID)

                  target_nodes <- nodes %>%
                  filter(start_end == 'end') %>%
                  pull(nodeID)

                  edges = edges %>%
                  mutate(from = source_nodes, to = target_nodes)

                  #remove duplicate nodes
                  nodes <- nodes %>%
                  distinct(nodeID, .keep_all = TRUE) %>%
                  select(-c(edgeID, start_end)) %>%
                  st_as_sf(coords = c('X', 'Y')) %>%
                  st_set_crs(st_crs(edges))

                  #change column names
                  roll <- edges[c('from','to','length')]
                  roll <- data.frame(roll)
                  roll <- roll[c('from','to','length')]
                  colnames(roll) <- c('from','to','weight')

                  coordinates <- nodes %>%
                  st_coordinates() %>%
                  as_tibble()
                  nodeID <- nodes[c('nodeID')]
                  coord <- cbind(coordinates,nodeID)
                  coord <- data.frame(coord)
                  coord <- coord[c('nodeID','X','Y')]
                  colnames(coord)<- c('ID','X','Y')

                  graph<-makegraph(roll,directed = F,coords = coord)

                  ###################
                  ##Shortest distance
                  ###################

                  #Loop over all bus stops within buffer
                  datalistA <- list()
                  h=2

                  for(h in 1:nrow(snap2_merged)){

                  test <- snap1
                  test2 <- snap2_merged[h,]


                  y <- coord[order(coord$ID),]
                  row.names(y) <- y$ID

                  node_location1 <- y %>% filter(y$Y %like% test$Y)
                  node_location1B <- node_location1$ID[1]

                  node_location2 <- y %>% filter(y$Y %like% test2$Y)
                  node_location2B <- node_location2$ID[1]

                  origin <- as.data.frame(node_location1B)
                  destination <- as.data.frame(node_location2B)
                  distance<-get_distance_pair(graph,from=origin,to=destination)
                  distance <- as.data.frame(distance)
                  distance <- distance[1,]
                  distance <- as.data.frame(distance)
                  temps <- (distance/(4.3*1000))*60
                  names(temps)[1] <- "walk_time"

                  datalistA[[h]] <- temps }

                  ALL <- dplyr::bind_rows(datalistA) #Deze tabel bevat de tijd om te stappen van piscine naar alle bushaltes binnen buffer

                  #Verbind opnieuw met comps
                  comps <- cbind(comps, ALL)

                  ################################################################################################################################################


        ###
        #Loop over all bus stops inside the buffer around piscine
        ###
        datalist2 <- list()
        i=1
        for(i in 1:nrow(comps)){
          #Extract trip nr corresponding to the selected bus stop and merge time table
          A <- filter(comps, row_number()== i)
          AA <- A[c("trip_id", "stop_id", "walk_time")]
          AA <- st_drop_geometry(AA)
          A_merged <- merge(AA, stib_bus_times_filter, by = "trip_id")
          A_merged_unique <- A_merged[!duplicated(A_merged$stop_sequence),]

          #Extract the arrival time corresponding to the selected bus stop
          halte <- chron(times = comps$arrival_time[i])

          #Calculate the time difference between the selected bus stop and each of the other stops on the same trip
          B <- c()
          for (k in 1:nrow(A_merged_unique)) {
            if (A_merged_unique$arrival_time[k] >= halte) {
              B[k] <- A_merged_unique$arrival_time[k] - halte
            } else {
              B[k] <- halte - A_merged_unique$arrival_time[k]
            }
          }

          #Convert the time difference to hh:mm:ss and add column to datatable
          BB <- chron(times = B)
          BBB <- 60 * 24 * as.numeric(times(BB))

          C <- cbind(A_merged_unique, BBB)

          #Extract stops at 20 minutes or less from the selected stop
          #reachable <- filter(C, C$BBB <= "20")  DEZE STAP WERKT NIET ???
          reachable <- C

          #Calculate 20minutes - BBB (travel time on bus) - walk_time (travel time by foot from piscine to bus stop)
          Diff20 <- 20-reachable$BBB-reachable$walk_time
          reachable <- cbind(reachable, Diff20)

          #Remove rows with Diff20 < 0
          reachable <- filter(reachable, reachable$Diff20 >= "0")

          #Convert from dataframe to sf again
          reachable_sf <- st_as_sf(reachable)

                        #st_write(reachable_sf, dsn ="J:/SET-SADL_User-DI0222/Projecten/Brussel-10-min/04 Model/Processing/Isochrones_R", layer = "Piscines reachable stops", driver = "ESRI Shapefile", append = F, overwrite=T)
          Start_busstop <- comps[i,]$descr_fr
          Start_busstop <- as.data.frame(Start_busstop)

          ###
          #Isochrone around reachable stops
          ###
          reachable_sf <- reachable_sf %>% mutate(Id = row_number())
          datalist <- list()
          j=1
          #j=3
          for (j in 1:nrow(reachable_sf)){
            row_interest <- filter(reachable_sf, row_number() == j)

            End_busstop <- row_interest$descr_fr
            End_busstop <- as.data.frame(End_busstop)

            ########################################################################################################

            options(digits = 15)
            st_crs(row_interest) <- st_crs("+init=epsg:31370")

            #Snap points piscines on road network
            library("maptools")
            location_sp <- as(row_interest, 'Spatial')
            location_sp <- SpatialPoints(location_sp)
            roads_sp <- as(roads, 'Spatial')
            test <- snapPointsToLines(location_sp,roads_sp)
            test2 <- as.data.frame(test)

            #Split roadnetwork on snapped points
            library("lwgeom")
            test3 <- st_as_sf(test2,coords = c("X", "Y"))
            on_line_all = st_cast(test3, "POINT")
            buf_all <- st_combine(st_buffer(on_line_all,0.0000000001))
            parts_all = st_collection_extract(lwgeom::st_split(roads$geometry, buf_all),"LINESTRING")

            parts_all = st_as_sf(
              data.frame(
                id = 1:length(parts_all),
                geometry = parts_all
              )
            )

            parts_all$length <- st_length(parts_all)

            #This is the roadnetwork we use to calculate the isochrone
            roads <- parts_all


            #give each edge a unique index (edges = afzonderlijke lijntjes)
            edges <- roads %>%
              mutate(edgeID = c(1:n()))

            #create nodes at the start and end point of each edge (nodes vormen begin en eindpunt van een edge)
            nodes <- edges %>%
              st_coordinates() %>%
              as_tibble() %>%
              rename(edgeID = L1) %>%
              group_by(edgeID) %>%
              slice(c(1, n())) %>%
              ungroup() %>%
              mutate(start_end = rep(c('start', 'end'), times = n()/2))

            #give each node a unique index (nodes komen dubbel voor omdat edges op elkaar aansluiten)
            library(tidyverse)
            nodes <- nodes %>%
              mutate(xy = paste(.$X, .$Y)) %>%
              group_by(X, Y) %>%
              mutate(nodeID =cur_group_id())
              #mutate(nodeID = group_indices(., factor(xy, levels = unique(xy)))) %>%
            nodes <- nodes[,c(-5)]


            #combine the node indices with the edges (om de vorm van de functie graph goed te krijgen)
            source_nodes <- nodes %>%
              filter(start_end == 'start') %>%
              pull(nodeID)

            target_nodes <- nodes %>%
              filter(start_end == 'end') %>%
              pull(nodeID)

            edges = edges %>%
              mutate(from = source_nodes, to = target_nodes)

            #remove duplicate nodes
            nodes <- nodes %>%
              distinct(nodeID, .keep_all = TRUE) %>%
              select(-c(edgeID, start_end)) %>%
              st_as_sf(coords = c('X', 'Y')) %>%
              st_set_crs(st_crs(edges))

            #change column names (om de vorm van de graph functie goed te krijgen)
            roadsA <- edges[c('from','to','length')]
            roadsA <- data.frame(roadsA)
            roadsA <- roadsA[c('from','to','length')]
            colnames(roadsA) <- c('from','to','weight')

            coordinates <- nodes %>%
              st_coordinates() %>%
              as_tibble()
            nodeID <- nodes[c('nodeID')]
            coord <- cbind(coordinates,nodeID)
            coord <- data.frame(coord)
            coord <- coord[c('nodeID','X','Y')]
            colnames(coord)<- c('ID','X','Y')

            graph<-makegraph(roadsA,directed = F,coords = coord)

            #walking min/speed/distance
            temps <- row_interest$Diff20
            lim <- (4.3*1000/60*temps)
            lim <- as.numeric(lim)
            lim <- as.data.frame(lim)


            #Match node ID with snapped bus stop (same coordinates X and Y)

            ########################################################## Dit deeltje kan volgens mij simpeler door de nodeID te halen uit coord$ID die dezelfde X en Y heeft als van het snapped point j (test2)
            #y <- coord[order(coord$ID),]
            #row.names(y) <- y$ID
            #node <- data.frame()
            #node_tot <- data.frame()
            #for (g in 1:dim(test2)[1]) {
              #node_loop <- node_tot
              #node <- subset(y$ID, y$Y %like% test2[g,]$Y)
              #node_tot <- rbind(node_loop, node)
            #}
            #node_isochrones <- node_tot[,1]
            #node_isochrones <- data.frame(node_isochrones)
            #colnames(node_isochrones) <- "nodeID"
            ##########################################################

            hey <- filter(coord, Y %like% test2$Y | X %like% test2$X)
            node_isochrones <- hey[1,1]


            #Compute isochrone
            iso<-get_isochrone(graph,from = node_isochrones,lim = c(lim))

            #Convert nodes to concave polygons with concaveman package
            coord$ID <- as.character(coord$ID)
            poly<-lapply(iso,function(t){
              t<-data.frame(noeuds=t,stringsAsFactors = F)
              t<-left_join(t,coord,by=c("noeuds"="ID"))
              return(concaveman(summarise(st_as_sf(t,coords=c("X","Y"),crs=31370))))
            })

            poly <- st_zm(poly)
            poly<-do.call(rbind,poly)
            poly <- cbind(poly, Start_busstop, End_busstop)


            #Delete geometries which are not correct due to errors in the road network
            #invalid <- st_coordinates(poly$polygons)
            #invalid <- as.data.frame(invalid)
            #invalid$L2 <- as.character(invalid$L2)
            #invalid <- count(invalid, invalid$L2)
            #invalid2 <- invalid[invalid$n<4, ]
            #poly$ID <- row.names(poly)
            #poly <- poly[!(poly$ID %in% invalid2$`invalid$L2`),]
            #poly <- poly %>% select(-ID)

            #ay <- st_drop_geometry(row_interest)
            #polyay <- cbind(ay, poly)


            #######################################################################################################

            datalist[[j]] <- poly
          }
            iso_ <- dplyr::bind_rows(datalist)

          datalist2[[i]] <- iso_
        }

        isochrones_piscine <- dplyr::bind_rows(datalist2)



        datalist3[[m]] <- isochrones_piscine

      #}

      Isochrones_ALL <- dplyr::bind_rows(datalist3)
      Isochrones_ALL$polygons <- st_geometry(Isochrones_ALL$polygons)


      Isochrones_ALL$mode <- selection1[1]
      Isochrones_ALL$theme <- selection6[1]
      Isochrones_ALL$soustheme <- selection7[1]
      Isochrones_ALL$minutes <- selection5[1]
      Isochrones_ALL$scenario <- selection8[1]

      a <- sub(".*?/(.*?).shp.*", "\\1", selection2[i])
      b <- sub(".*?/(.*?).shp.*", "\\1", selection3[1])

      #write to shapefile
      #destination folder specified as user parameter
      destination <- c(file.path(selection4[1]))
      st_write(Isochrones_ALL, dsn = destination, layer =  paste0(a,"_",selection1[1],"_",selection5[1],"_", b,"_",selection11[1]), driver = "ESRI Shapefile", append = F, overwrite=T)
      ,time cost.level modus X Y L1 L2 test lim
    R_SCRIPT:
      ########################################################################################
      ############################### Calculation of isochrones ##############################
      ########################################################################################

      #cpprouting method to calculate isochrones

      #More information:
      #https://cran.r-project.org/web/packages/cppRouting/cppRouting.pdf
      #https://github.com/vlarmet/cppRouting/blob/master/README.md#compute-isochrones
      #https://r-spatial.org/r/2019/09/26/spatial-networks.html

      #set the number of digits
      options(digits = 15)

      #installation of packages
      #installation of packages
      if(!"remotes" %in% installed.packages()) {
        install.packages("remotes")
      }

      cran_pkgs = c(
        "sf",
        "maptools",
        "tidyverse",
        "foreach",
        "chron",
        "tibbletime",
        "dplyr",
        "data.table",
        "cppRouting",
        "concaveman",
        "ggmap",
        "tmap",
        "microbenchmark",
        "reshape2",
        "sp",
        "rgdal",
        "tidygraph",
        "igraph",
        "tibble",
        "units",
        "osmdata",
        "rgrass7",
        "link2GI",
        "nabor",
        "ggplot2",
        "lwgeom",
        "magritrr"
      )

      library(sf)
      library(maptools)
      library(tidyverse)
      library(foreach)
      library(chron)
      library(tibbletime)
      library(dplyr)
      library(data.table)
      library(cppRouting)
      library(concaveman)
      library(ggmap)
      library(tmap)
      library(microbenchmark)
      library(reshape2)
      library(sp)
      library(rgdal)
      library(tidygraph)
      library(igraph)
      library(tibble)
      library(units)
      library(osmdata)
      library(rgrass7)
      library(link2GI)
      library(nabor)

      #preparation of the data based on user parameters

      selection1 <- Output_2$mode
      selection2 <- Output00$X_list
      selection3 <- Output01$réseau_routier
      selection4 <- Output02$destination
      selection5 <- Output03$minutes
      selection6 <- Output_2$theme
      selection7 <- Output_2$soustheme
      selection8 <- Output_2$scenario
      selection9 <- Output01$STOP_times
      selection10 <- Output01$STIB_Bus
      selection11 <- Output$numero


      #read shapefile data
      #based on file path provided as user parameter for 'reseau_routier', 'STOP_times', 'STIB_Bus', 'variable'
      stops <- read.table(file.path(selection9[1]), header = T, sep = ",")
      piscines <- st_read(file.path(selection2[1]))
      stib_bus <- st_read(file.path(selection10[1]))
      roads <- st_read(file.path(selection3[1]))

      #Prepare stop_times.txt data
      arrival_time <- chron(times= stops$arrival_time)
      times <- as.data.frame(arrival_time)
      stops_subset <- subset(stops, select = c(trip_id, stop_id, stop_sequence))
      stops_times <- cbind.data.frame(stops_subset, times)

      #Add stop_times table to stib_bus shapefile
      stib_bus_times <- merge(stib_bus, stops_times, by = "stop_id")

      #Filter out afternoon trips
      stib_bus_times_filter <- filter(stib_bus_times, arrival_time >= "14:00:00", arrival_time <= "19:00:00")

      #Remove duplicate stop_id
      stib_bus_times_unique <- stib_bus_times_filter[!duplicated(stib_bus_times_filter$stop_id),]

      #Add ID number to piscines
      piscines <- piscines %>% mutate(Id = row_number())

      ###################
      ##For all piscines
      ###################


      m=selection11[1]
      datalist3 = list()
      #for(m in 1:nrow(piscines)){

        #Buffer distance around piscine
        l = 500

        #Isolate the row as the origin point:
        row_interest <- filter(piscines, row_number()== m)

        Id <- row_interest$Id
        Id <- as.data.frame(Id)
        #Name <- row_interest$name
        #Name_piscine <- as.data.frame(Name)

        #Create the buffer:
        buffer <- row_interest %>% st_buffer(dist = l)
        st_crs(buffer) <- st_crs("+init=epsg:31370")
        st_crs(stib_bus_times_unique) <- st_crs("+init=epsg:31370")

                    #st_write(buffer, dsn ="J:/SET-SADL_User-DI0222/Projecten/Brussel-10-min/04 Model/Processing/Isochrones_R", layer = "Piscine triton buffer", driver = "ESRI Shapefile", append = F, overwrite=T)


        #Extract the row numbers of the neighbors
        comps_idx <- st_intersects(buffer, stib_bus_times_unique)[[1]]
        comps_idx <- as.data.frame(comps_idx)

         #Remove piscines for which there is no overlap between buffer and any bus stop
        #if (dim(comps_idx)[1] == 0) {
        #next
        #}

        comps_idx <- as.integer(as.character(comps_idx$comps_idx))


        #Get all the neighbors:
        comps <- stib_bus_times_unique %>% filter(row_number() %in% comps_idx)
        comps <- comps %>% mutate(Id = row_number())

                  #############################################################################################################################################################################################
                  #Calculation walking time between piscine and bus stops within buffer around piscine
                  ####################################################################################

                  options(digits = 15)

                  #Project piscine and bus stops onto the street network
                  location1 <- row_interest
                  location2 <- comps
                  urbis <- roads
                  st_crs(urbis) <- st_crs("+init=epsg:31370")
                  st_crs(location1) <- st_crs("+init=epsg:31370")
                  st_crs(location2) <- st_crs("+init=epsg:31370")

                  library("maptools")
                  location1_sp <- as(location1, 'Spatial')
                  location1_sp <- SpatialPoints(location1_sp)
                  location2_sp <- as(location2, 'Spatial')
                  location2_sp <- SpatialPoints(location2_sp)
                  urbis_sp <- as(urbis, 'Spatial')
                  snap1 <- snapPointsToLines(location1_sp,urbis_sp)
                  snap1 <- as.data.frame(snap1)
                  snap2 <- snapPointsToLines(location2_sp,urbis_sp)
                  snap2 <- as.data.frame(snap2)
                  snap2 <- snap2 %>% mutate(Id = row_number())
                  snap2_merged <- merge(snap2, comps, by = "Id")

                  #Split the street network where piscine and bus stops project onto network
                  library("lwgeom")
                  test3 <- st_as_sf(snap1,coords = c("X", "Y"))
                  on_line_all = st_cast(test3, "POINT")
                  buf_all <- st_combine(st_buffer(on_line_all,0.0000000001))
                  parts_all = st_collection_extract(lwgeom::st_split(urbis$geometry, buf_all),"LINESTRING")

                  parts_all = st_as_sf(
                      data.frame(
                      id = 1:length(parts_all),
                      geometry = parts_all
                      )
                  )

                  parts_all$length <- st_length(parts_all)

                  urbis <- parts_all

                  library("lwgeom")
                  test4 <- st_as_sf(snap2,coords = c("X", "Y"))
                  on_line_all = st_cast(test4, "POINT")
                  buf_all <- st_combine(st_buffer(on_line_all,0.0000000001))
                  parts_all = st_collection_extract(lwgeom::st_split(urbis$geometry, buf_all),"LINESTRING")

                  parts_all = st_as_sf(
                      data.frame(
                      id = 1:length(parts_all),
                      geometry = parts_all
                      )
                  )

                  parts_all$length <- st_length(parts_all)

                  urbis <- parts_all

                  #give each edge a unique index
                  edges <- urbis %>%
                  mutate(edgeID = c(1:n()))

                  #create nodes at the start and end point of each edge
                  nodes <- edges %>%
                  st_coordinates() %>%
                  as_tibble() %>%
                  mutate(edgeID = L1) %>%
                  group_by(edgeID) %>%
                  slice(c(1, n())) %>%
                  ungroup() %>%
                  mutate(start_end = rep(c('start', 'end'), times = n()/2))

                  #give each node a unique index
                  library(tidyverse)
                  nodes <- nodes %>%
                  mutate(xy = paste(.$X, .$Y)) %>%
                  group_by(X, Y) %>%
                  mutate(nodeID =cur_group_id()) %>%
                  #mutate(nodeID = group_indices(., factor(xy, levels = unique(xy)))) %>%
                  select(-xy)

                  #combine the node indices with the edges
                  source_nodes <- nodes %>%
                  filter(start_end == 'start') %>%
                  pull(nodeID)

                  target_nodes <- nodes %>%
                  filter(start_end == 'end') %>%
                  pull(nodeID)

                  edges = edges %>%
                  mutate(from = source_nodes, to = target_nodes)

                  #remove duplicate nodes
                  nodes <- nodes %>%
                  distinct(nodeID, .keep_all = TRUE) %>%
                  select(-c(edgeID, start_end)) %>%
                  st_as_sf(coords = c('X', 'Y')) %>%
                  st_set_crs(st_crs(edges))

                  #change column names
                  roll <- edges[c('from','to','length')]
                  roll <- data.frame(roll)
                  roll <- roll[c('from','to','length')]
                  colnames(roll) <- c('from','to','weight')

                  coordinates <- nodes %>%
                  st_coordinates() %>%
                  as_tibble()
                  nodeID <- nodes[c('nodeID')]
                  coord <- cbind(coordinates,nodeID)
                  coord <- data.frame(coord)
                  coord <- coord[c('nodeID','X','Y')]
                  colnames(coord)<- c('ID','X','Y')

                  graph<-makegraph(roll,directed = F,coords = coord)

                  ###################
                  ##Shortest distance
                  ###################

                  #Loop over all bus stops within buffer
                  datalistA <- list()
                  h=2

                  for(h in 1:nrow(snap2_merged)){

                  test <- snap1
                  test2 <- snap2_merged[h,]


                  y <- coord[order(coord$ID),]
                  row.names(y) <- y$ID

                  node_location1 <- y %>% filter(y$Y %like% test$Y)
                  node_location1B <- node_location1$ID[1]

                  node_location2 <- y %>% filter(y$Y %like% test2$Y)
                  node_location2B <- node_location2$ID[1]

                  origin <- as.data.frame(node_location1B)
                  destination <- as.data.frame(node_location2B)
                  distance<-get_distance_pair(graph,from=origin,to=destination)
                  distance <- as.data.frame(distance)
                  distance <- distance[1,]
                  distance <- as.data.frame(distance)
                  temps <- (distance/(4.3*1000))*60
                  names(temps)[1] <- "walk_time"

                  datalistA[[h]] <- temps }

                  ALL <- dplyr::bind_rows(datalistA) #Deze tabel bevat de tijd om te stappen van piscine naar alle bushaltes binnen buffer

                  #Verbind opnieuw met comps
                  comps <- cbind(comps, ALL)

                  ################################################################################################################################################


        ###
        #Loop over all bus stops inside the buffer around piscine
        ###
        datalist2 <- list()
        i=1
        for(i in 1:nrow(comps)){
          #Extract trip nr corresponding to the selected bus stop and merge time table
          A <- filter(comps, row_number()== i)
          AA <- A[c("trip_id", "stop_id", "walk_time")]
          AA <- st_drop_geometry(AA)
          A_merged <- merge(AA, stib_bus_times_filter, by = "trip_id")
          A_merged_unique <- A_merged[!duplicated(A_merged$stop_sequence),]

          #Extract the arrival time corresponding to the selected bus stop
          halte <- chron(times = comps$arrival_time[i])

          #Calculate the time difference between the selected bus stop and each of the other stops on the same trip
          B <- c()
          for (k in 1:nrow(A_merged_unique)) {
            if (A_merged_unique$arrival_time[k] >= halte) {
              B[k] <- A_merged_unique$arrival_time[k] - halte
            } else {
              B[k] <- halte - A_merged_unique$arrival_time[k]
            }
          }

          #Convert the time difference to hh:mm:ss and add column to datatable
          BB <- chron(times = B)
          BBB <- 60 * 24 * as.numeric(times(BB))

          C <- cbind(A_merged_unique, BBB)

          #Extract stops at 20 minutes or less from the selected stop
          #reachable <- filter(C, C$BBB <= "20")  DEZE STAP WERKT NIET ???
          reachable <- C

          #Calculate 20minutes - BBB (travel time on bus) - walk_time (travel time by foot from piscine to bus stop)
          Diff20 <- 20-reachable$BBB-reachable$walk_time
          reachable <- cbind(reachable, Diff20)

          #Remove rows with Diff20 < 0
          reachable <- filter(reachable, reachable$Diff20 >= "0")

          #Convert from dataframe to sf again
          reachable_sf <- st_as_sf(reachable)

                        #st_write(reachable_sf, dsn ="J:/SET-SADL_User-DI0222/Projecten/Brussel-10-min/04 Model/Processing/Isochrones_R", layer = "Piscines reachable stops", driver = "ESRI Shapefile", append = F, overwrite=T)
          Start_busstop <- comps[i,]$descr_fr
          Start_busstop <- as.data.frame(Start_busstop)

          ###
          #Isochrone around reachable stops
          ###
          reachable_sf <- reachable_sf %>% mutate(Id = row_number())
          datalist <- list()
          j=1
          #j=3
          for (j in 1:nrow(reachable_sf)){
            row_interest <- filter(reachable_sf, row_number() == j)

            End_busstop <- row_interest$descr_fr
            End_busstop <- as.data.frame(End_busstop)

            ########################################################################################################

            options(digits = 15)
            st_crs(row_interest) <- st_crs("+init=epsg:31370")

            #Snap points piscines on road network
            library("maptools")
            location_sp <- as(row_interest, 'Spatial')
            location_sp <- SpatialPoints(location_sp)
            roads_sp <- as(roads, 'Spatial')
            test <- snapPointsToLines(location_sp,roads_sp)
            test2 <- as.data.frame(test)

            #Split roadnetwork on snapped points
            library("lwgeom")
            test3 <- st_as_sf(test2,coords = c("X", "Y"))
            on_line_all = st_cast(test3, "POINT")
            buf_all <- st_combine(st_buffer(on_line_all,0.0000000001))
            parts_all = st_collection_extract(lwgeom::st_split(roads$geometry, buf_all),"LINESTRING")

            parts_all = st_as_sf(
              data.frame(
                id = 1:length(parts_all),
                geometry = parts_all
              )
            )

            parts_all$length <- st_length(parts_all)

            #This is the roadnetwork we use to calculate the isochrone
            roads <- parts_all


            #give each edge a unique index (edges = afzonderlijke lijntjes)
            edges <- roads %>%
              mutate(edgeID = c(1:n()))

            #create nodes at the start and end point of each edge (nodes vormen begin en eindpunt van een edge)
            nodes <- edges %>%
              st_coordinates() %>%
              as_tibble() %>%
              rename(edgeID = L1) %>%
              group_by(edgeID) %>%
              slice(c(1, n())) %>%
              ungroup() %>%
              mutate(start_end = rep(c('start', 'end'), times = n()/2))

            #give each node a unique index (nodes komen dubbel voor omdat edges op elkaar aansluiten)
            library(tidyverse)
            nodes <- nodes %>%
              mutate(xy = paste(.$X, .$Y)) %>%
              group_by(X, Y) %>%
              mutate(nodeID =cur_group_id())
              #mutate(nodeID = group_indices(., factor(xy, levels = unique(xy)))) %>%
            nodes <- nodes[,c(-5)]


            #combine the node indices with the edges (om de vorm van de functie graph goed te krijgen)
            source_nodes <- nodes %>%
              filter(start_end == 'start') %>%
              pull(nodeID)

            target_nodes <- nodes %>%
              filter(start_end == 'end') %>%
              pull(nodeID)

            edges = edges %>%
              mutate(from = source_nodes, to = target_nodes)

            #remove duplicate nodes
            nodes <- nodes %>%
              distinct(nodeID, .keep_all = TRUE) %>%
              select(-c(edgeID, start_end)) %>%
              st_as_sf(coords = c('X', 'Y')) %>%
              st_set_crs(st_crs(edges))

            #change column names (om de vorm van de graph functie goed te krijgen)
            roadsA <- edges[c('from','to','length')]
            roadsA <- data.frame(roadsA)
            roadsA <- roadsA[c('from','to','length')]
            colnames(roadsA) <- c('from','to','weight')

            coordinates <- nodes %>%
              st_coordinates() %>%
              as_tibble()
            nodeID <- nodes[c('nodeID')]
            coord <- cbind(coordinates,nodeID)
            coord <- data.frame(coord)
            coord <- coord[c('nodeID','X','Y')]
            colnames(coord)<- c('ID','X','Y')

            graph<-makegraph(roadsA,directed = F,coords = coord)

            #walking min/speed/distance
            temps <- row_interest$Diff20
            lim <- (4.3*1000/60*temps)
            lim <- as.numeric(lim)
            lim <- as.data.frame(lim)


            #Match node ID with snapped bus stop (same coordinates X and Y)

            ########################################################## Dit deeltje kan volgens mij simpeler door de nodeID te halen uit coord$ID die dezelfde X en Y heeft als van het snapped point j (test2)
            #y <- coord[order(coord$ID),]
            #row.names(y) <- y$ID
            #node <- data.frame()
            #node_tot <- data.frame()
            #for (g in 1:dim(test2)[1]) {
              #node_loop <- node_tot
              #node <- subset(y$ID, y$Y %like% test2[g,]$Y)
              #node_tot <- rbind(node_loop, node)
            #}
            #node_isochrones <- node_tot[,1]
            #node_isochrones <- data.frame(node_isochrones)
            #colnames(node_isochrones) <- "nodeID"
            ##########################################################

            hey <- filter(coord, Y %like% test2$Y | X %like% test2$X)
            node_isochrones <- hey[1,1]


            #Compute isochrone
            iso<-get_isochrone(graph,from = node_isochrones,lim = c(lim))

            #Convert nodes to concave polygons with concaveman package
            coord$ID <- as.character(coord$ID)
            poly<-lapply(iso,function(t){
              t<-data.frame(noeuds=t,stringsAsFactors = F)
              t<-left_join(t,coord,by=c("noeuds"="ID"))
              return(concaveman(summarise(st_as_sf(t,coords=c("X","Y"),crs=31370))))
            })

            poly <- st_zm(poly)
            poly<-do.call(rbind,poly)
            poly <- cbind(poly, Start_busstop, End_busstop)


            #Delete geometries which are not correct due to errors in the road network
            #invalid <- st_coordinates(poly$polygons)
            #invalid <- as.data.frame(invalid)
            #invalid$L2 <- as.character(invalid$L2)
            #invalid <- count(invalid, invalid$L2)
            #invalid2 <- invalid[invalid$n<4, ]
            #poly$ID <- row.names(poly)
            #poly <- poly[!(poly$ID %in% invalid2$`invalid$L2`),]
            #poly <- poly %>% select(-ID)

            #ay <- st_drop_geometry(row_interest)
            #polyay <- cbind(ay, poly)


            #######################################################################################################

            datalist[[j]] <- poly
          }
            iso_ <- dplyr::bind_rows(datalist)

          datalist2[[i]] <- iso_
        }

        isochrones_piscine <- dplyr::bind_rows(datalist2)



        datalist3[[m]] <- isochrones_piscine

      #}

      Isochrones_ALL <- dplyr::bind_rows(datalist3)
      Isochrones_ALL$polygons <- st_geometry(Isochrones_ALL$polygons)


      Isochrones_ALL$mode <- selection1[1]
      Isochrones_ALL$theme <- selection6[1]
      Isochrones_ALL$soustheme <- selection7[1]
      Isochrones_ALL$minutes <- selection5[1]
      Isochrones_ALL$scenario <- selection8[1]

      a <- sub(".*?/(.*?).shp.*", "\\1", selection2[i])
      b <- sub(".*?/(.*?).shp.*", "\\1", selection3[1])

      #write to shapefile
      #destination folder specified as user parameter
      destination <- c(file.path(selection4[1]))
      st_write(Isochrones_ALL, dsn = destination, layer =  paste0(a,"_",selection1[1],"_",selection5[1],"_", b,"_",selection11[1]), driver = "ESRI Shapefile", append = F, overwrite=T)
    TABLE_DEF = Output_2,mode,varchar(200),theme,varchar(200),soustheme,varchar(200),scenario,varchar(200),_creation_instance,varchar(20),Output00,variable,varchar(200),X_creation_instance,varchar(20),_list,varchar(200),_element_index,varchar(200),Output01,réseau_routier,varchar(200),X_creation_instance,varchar(20),STIB_Bus,varchar(200),STOP_times,varchar(200),Output02,destination,varchar(200),X_creation_instance,varchar(20),Output03,minutes,varchar(200),X_creation_instance,varchar(20),Output,numero,varchar(200),X_creation_instance,varchar(20)

Bookmark: Remettre ensemble les isochrones + Adaptation
Piscine 1 (reader SHAPEFILE_1)
    attributes: Name varchar(80), Strt_bs varchar(80), End_bss varchar(80)
    -> Piscines (writer SHAPEFILE_27)
Piscine 2 (reader SHAPEFILE_1)
    attributes: Name varchar(80), Strt_bs varchar(80), End_bss varchar(80)
    -> Piscines (writer SHAPEFILE_27)
Piscine 3 (reader SHAPEFILE_1)
    attributes: Name varchar(80), Strt_bs varchar(80), End_bss varchar(80)
    -> Piscines (writer SHAPEFILE_27)
Piscine 4 (reader SHAPEFILE_1)
    attributes: Name varchar(80), Strt_bs varchar(80), End_bss varchar(80)
    -> Piscines (writer SHAPEFILE_27)
Piscine 5 (reader SHAPEFILE_1)
    attributes: Name varchar(80), Strt_bs varchar(80), End_bss varchar(80)
    -> Piscines (writer SHAPEFILE_27)
Piscine 6 (reader SHAPEFILE_1)
    attributes: Name varchar(80), Strt_bs varchar(80), End_bss varchar(80)
    -> Piscines (writer SHAPEFILE_27)
Piscine 7 (reader SHAPEFILE_1)
    attributes: Name varchar(80), Strt_bs varchar(80), End_bss varchar(80)
    -> Piscines (writer SHAPEFILE_27)
Piscine 9 (reader SHAPEFILE_1)
    attributes: Name varchar(80), Strt_bs varchar(80), End_bss varchar(80)
    -> Piscines (writer SHAPEFILE_27)
Piscine 10 (reader SHAPEFILE_1)
    attributes: Name varchar(80), Strt_bs varchar(80), End_bss varchar(80)
    -> Piscines (writer SHAPEFILE_27)
Piscine 11 (reader SHAPEFILE_1)
    attributes: Name varchar(80), Strt_bs varchar(80), End_bss varchar(80)
    -> Piscines (writer SHAPEFILE_27)
Piscine 12 (reader SHAPEFILE_1)
    attributes: Name varchar(80), Strt_bs varchar(80), End_bss varchar(80)
    -> Piscines (writer SHAPEFILE_27)
Piscine 13 (reader SHAPEFILE_1)
    attributes: Name varchar(80), Strt_bs varchar(80), End_bss varchar(80)
    -> Piscines (writer SHAPEFILE_27)
Piscine 14 (reader SHAPEFILE_1)
    attributes: Name varchar(80), Strt_bs varchar(80), End_bss varchar(80)
    -> Piscines (writer SHAPEFILE_27)
Piscine 15 (reader SHAPEFILE_1)
    attributes: Name varchar(80), Strt_bs varchar(80), End_bss varchar(80)
    -> Piscines (writer SHAPEFILE_27)
Piscines (writer SHAPEFILE_27)
    attributes: Name varchar(80), Strt_bs varchar(80), End_bss varchar(80)
Piscines (reader SHAPEFILE_25)
    attributes: Name varchar(80), Strt_bs varchar(80), End_bss varchar(80)
    -> AttributeManager
AttributeManager
    ATTR_TABLE:
      SET_TO mode = TP
      SET_TO theme = vivre ensemble
      SET_TO soustheme = sport
      SET_TO scenario = 2021
    -> piscine_TP_20_Urbis_cleaned (writer SHAPEFILE_30)
piscine_TP_20_Urbis_cleaned (writer SHAPEFILE_30)
    attributes: Name varchar(80), Strt_bs varchar(80), End_bss varchar(80), mode varchar(200), theme varchar(200), soustheme varchar(200), scenario varchar(200)
BA 1 (reader SHAPEFILE_2)
    attributes: Name varchar(80), Strt_bs varchar(80), End_bss varchar(80)
    -> BureauxAccueilPA_RBC (writer SHAPEFILE_28)
BA 2 (reader SHAPEFILE_3)
    attributes: Name varchar(80), Strt_bs varchar(80), End_bss varchar(80)
    -> BureauxAccueilPA_RBC (writer SHAPEFILE_28)
BA 3 (reader SHAPEFILE_4)
    attributes: Name varchar(80), Strt_bs varchar(80), End_bss varchar(80)
    -> BureauxAccueilPA_RBC (writer SHAPEFILE_28)
BA 4 (reader SHAPEFILE_5)
    attributes: Name varchar(80), Strt_bs varchar(80), End_bss varchar(80)
    -> BureauxAccueilPA_RBC (writer SHAPEFILE_28)
BA 5 (reader SHAPEFILE_6)
    attributes: Name varchar(80), Strt_bs varchar(80), End_bss varchar(80)
    -> BureauxAccueilPA_RBC (writer SHAPEFILE_28)
BA 6 (reader SHAPEFILE_7)
    attributes: Name varchar(80), Strt_bs varchar(80), End_bss varchar(80)
    -> BureauxAccueilPA_RBC (writer SHAPEFILE_28)
BA 7 (reader SHAPEFILE_8)
    attributes: Name varchar(80), Strt_bs varchar(80), End_bss varchar(80)
    -> BureauxAccueilPA_RBC (writer SHAPEFILE_28)
BA 8 (reader SHAPEFILE_9)
    attributes: Name varchar(80), Strt_bs varchar(80), End_bss varchar(80)
    -> BureauxAccueilPA_RBC (writer SHAPEFILE_28)
BA 9 (reader SHAPEFILE_10)
    attributes: Name varchar(80), Strt_bs varchar(80), End_bss varchar(80)
    -> BureauxAccueilPA_RBC (writer SHAPEFILE_28)
BureauxAccueilPA_RBC (writer SHAPEFILE_28)
    attributes: Name varchar(80), Strt_bs varchar(80), End_bss varchar(80)
BureauxAccueilPA_RBC (reader SHAPEFILE_24)
    attributes: Name varchar(80), Strt_bs varchar(80), End_bss varchar(80)
    -> AttributeManager_2
AttributeManager_2
    ATTR_TABLE:
      SET_TO mode = TP
      SET_TO theme = vivre ensemble
      SET_TO soustheme = cohesion sociale
      SET_TO scenario = 2021
    -> BureauxAccueilPA_RBC_TP_20_Urbis_cleaned (writer SHAPEFILE_31)
BureauxAccueilPA_RBC_TP_20_Urbis_cleaned (writer SHAPEFILE_31)
    attributes: Name varchar(80), Strt_bs varchar(80), End_bss varchar(80), mode varchar(200), theme varchar(200), soustheme varchar(200), scenario varchar(200)
Hopital (reader SHAPEFILE_26)
    attributes: Name varchar(80), Strt_bs varchar(80), End_bss varchar(80)
    -> AttributeManager_3
AttributeManager_3
    ATTR_TABLE:
      SET_TO mode = TP
      SET_TO theme = vivre ensemble
      SET_TO soustheme = sante
      SET_TO scenario = 2021
    -> Urgences_TP_20_Urbis_cleaned (writer SHAPEFILE_32)
Urgences_TP_20_Urbis_cleaned (writer SHAPEFILE_32)
    attributes: Name varchar(80), Strt_bs varchar(80), End_bss varchar(80), mode varchar(200), theme varchar(200), soustheme varchar(200), scenario varchar(200)
Hopital 1 (reader SHAPEFILE_11)
    attributes: Name varchar(80), Strt_bs varchar(80), End_bss varchar(80)
    -> Hopital (writer SHAPEFILE_29)
Hopital 2 (reader SHAPEFILE_12)
    attributes: Name varchar(113), Strt_bs varchar(80), End_bss varchar(80)
    -> Hopital (writer SHAPEFILE_29)
Hopital 3 (reader SHAPEFILE_13)
    attributes: Name varchar(80), Strt_bs varchar(80), End_bss varchar(80)
    -> Hopital (writer SHAPEFILE_29)
Hopital 4 (reader SHAPEFILE_14)
    attributes: Name varchar(80), Strt_bs varchar(80), End_bss varchar(80)
    -> Hopital (writer SHAPEFILE_29)
Hopital 5 (reader SHAPEFILE_15)
    attributes: Name varchar(89), Strt_bs varchar(80), End_bss varchar(80)
    -> Hopital (writer SHAPEFILE_29)
Hopital 6 (reader SHAPEFILE_16)
    attributes: Name varchar(80), Strt_bs varchar(80), End_bss varchar(80)
    -> Hopital (writer SHAPEFILE_29)
Hopital 7 (reader SHAPEFILE_17)
    attributes: Name varchar(80), Strt_bs varchar(80), End_bss varchar(80)
    -> Hopital (writer SHAPEFILE_29)
Hopital 8 (reader SHAPEFILE_18)
    attributes: Name varchar(80), Strt_bs varchar(80), End_bss varchar(80)
    -> Hopital (writer SHAPEFILE_29)
Hopital 9 (reader SHAPEFILE_19)
    attributes: Name varchar(116), Strt_bs varchar(80), End_bss varchar(80)
    -> Hopital (writer SHAPEFILE_29)
Hopital 10 (reader SHAPEFILE_20)
    attributes: Name varchar(116), Strt_bs varchar(80), End_bss varchar(80)
    -> Hopital (writer SHAPEFILE_29)
Hopital 11 (reader SHAPEFILE_21)
    attributes: Name varchar(80), Strt_bs varchar(80), End_bss varchar(80)
    -> Hopital (writer SHAPEFILE_29)
Hopital 12 (reader SHAPEFILE_22)
    attributes: Name varchar(116), Strt_bs varchar(80), End_bss varchar(80)
    -> Hopital (writer SHAPEFILE_29)
Hopital 13 (reader SHAPEFILE_23)
    attributes: Name varchar(80), Strt_bs varchar(80), End_bss varchar(80)
    -> Hopital (writer SHAPEFILE_29)
Hopital (writer SHAPEFILE_29)
    attributes: Name varchar(113), Strt_bs varchar(80), End_bss varchar(80)
