FME workspace Cleaning Urbis.fmw

Parameters:
- DestDataset_SHAPEFILE =
- DestDataset_SHAPEFILE_2 =
- DestDataset_SHAPEFILE_3 =
- SourceDataset_SHAPEFILE =
- SourceDataset_SHAPEFILE_5 =
- SourceDataset_SHAPEFILE_6 =
- SourceDataset_SHAPEFILE_7 =

Readers:
- SHAPEFILE_1: SHAPEFILE from $(SourceDataset_SHAPEFILE)
- SHAPEFILE_2: SHAPEFILE from $(SourceDataset_SHAPEFILE_5)
- SHAPEFILE_3: SHAPEFILE from $(SourceDataset_SHAPEFILE_7)
- SHAPEFILE_4: SHAPEFILE from $(SourceDataset_SHAPEFILE_6)

Writers:
- SHAPEFILE_5: SHAPEFILE to $(DestDataset_SHAPEFILE_2)
- SHAPEFILE_6: SHAPEFILE to $(DestDataset_SHAPEFILE)
- SHAPEFILE_7: SHAPEFILE to $(DestDataset_SHAPEFILE_3)

UrbAdm_STREET_AXIS (reader SHAPEFILE_1)
    attributes: ID long, VERSIONID number(38,0), SN_ID_B long, SN_ID_E long, LENGTH float, SLOPE float, TYPE varchar(5), LEVEL_Z long, FLOW varchar(15), INSPIRE_ID varchar(50), BEGIN_LIFE date, END_LIFE date
    -> TestFilter
TestFilter
    DEFAULT_VALUE = <UNFILTERED>
    TEST_LIST = "BOOL_OP,OR,COMPOSITE_TEST,""""""1"""""",TEST_CLAUSE,TEST @Value(TYPE) != C",All but C
    All but C -> LineOnAreaOverlayer [LINE]
    All but C -> LineOnAreaOverlayer_2 [LINE]
    All but C -> LineOnAreaOverlayer_3 [LINE]
UrbAdm_STREET_SURFACE_LEVEL0 (reader SHAPEFILE_2)
    attributes: ID long,Indexed, VERSIONID long, TYPE varchar(5), PN_ID long, LEVEL_Z long, PNMC varchar(60), AREA float, ADMIN varchar(30), ADM_VALID varchar(1), HIERARCHY varchar(5), HIER_VALID varchar(1), PN_NAME_FR varchar(60), PN_NAME_DU varchar(60), MU_NAME_FR varchar(60), MU_NAME_DU varchar(60), MU_NAT_COD varchar(15), PZ_NAT_COD varchar(4), INSPIRE_ID varchar(50), BEGIN_LIFE date, END_LIFE date
    -> LineOnAreaOverlayer [AREA]
LineOnAreaOverlayer
    ATTR_ACCUM_MODE = Merge Incoming
    ATTR_CONFLICT_RES = Use Original
    CLEANING_TOLERANCE = Automatic
    DEAGGREGATE_INPUT = Yes
    LIST_ATTRS_TO_INCLUDE = HIERARCHY
    LIST_NAME = Hierarchy
    OV_ATTR = _overlaps
    LINE -> TestFilter_2
TestFilter_2
    DEFAULT_VALUE = <UNFILTERED>
    TEST_LIST = "BOOL_OP,OR,COMPOSITE_TEST,""""""1"""""",TEST_CLAUSE,TEST @Value(_overlaps) != 0",All but 0
    All but 0 -> TestFilter_5
TestFilter_5
    DEFAULT_VALUE = <UNFILTERED>
    TEST_LIST = "BOOL_OP,OR,COMPOSITE_TEST,""""""1"""""",TEST_CLAUSE,TEST @Value(HIERARCHY) != H",All but H
    All but H -> Urbis cleaned (writer SHAPEFILE_7)
UrbAdm_STREET_SURFACE_LEVEL_PLUS1 (reader SHAPEFILE_3)
    attributes: ID long, VERSIONID long, TYPE varchar(5), PN_ID long, LEVEL_Z long, PNMC varchar(60), AREA float, ADMIN varchar(30), ADM_VALID varchar(1), HIERARCHY varchar(5), HIER_VALID varchar(1), PN_NAME_FR varchar(60), PN_NAME_DU varchar(60), MU_NAME_FR varchar(60), MU_NAME_DU varchar(60), MU_NAT_COD varchar(15), PZ_NAT_COD varchar(4), INSPIRE_ID varchar(50), BEGIN_LIFE date, END_LIFE date
    -> LineOnAreaOverlayer_2 [AREA]
LineOnAreaOverlayer_2
    ATTR_ACCUM_MODE = Merge Incoming
    ATTR_CONFLICT_RES = Use Original
    CLEANING_TOLERANCE = Automatic
    DEAGGREGATE_INPUT = Yes
    OV_ATTR = _overlaps
    LINE -> TestFilter_3
TestFilter_3
    DEFAULT_VALUE = <UNFILTERED>
    TEST_LIST = "BOOL_OP,OR,COMPOSITE_TEST,""""""1"""""",TEST_CLAUSE,TEST @Value(_overlaps) != 0",All but 0
    All but 0 -> TestFilter_6
TestFilter_6
    DEFAULT_VALUE = <UNFILTERED>
    TEST_LIST = "BOOL_OP,OR,COMPOSITE_TEST,""""""1"""""",TEST_CLAUSE,TEST @Value(HIERARCHY) != H",All but H
    All but H -> Urbis cleaned (writer SHAPEFILE_7)
Urbis cleaned (writer SHAPEFILE_7)
    attributes: ID long, VERSIONID number(38,0), SN_ID_B long, SN_ID_E long, LENGTH float, SLOPE float, TYPE varchar(5), LEVEL_Z long, FLOW varchar(15), INSPIRE_ID varchar(50), BEGIN_LIFE date, END_LIFE date
UrbAdm_STREET_SURFACE_LEVEL_MINUS1 (reader SHAPEFILE_4)
    attributes: ID long, VERSIONID long, TYPE varchar(5), PN_ID long, LEVEL_Z long, PNMC varchar(60), AREA float, ADMIN varchar(30), ADM_VALID varchar(1), HIERARCHY varchar(5), HIER_VALID varchar(1), PN_NAME_FR varchar(60), PN_NAME_DU varchar(60), MU_NAME_FR varchar(60), MU_NAME_DU varchar(60), MU_NAT_COD varchar(15), PZ_NAT_COD varchar(4), INSPIRE_ID varchar(50), BEGIN_LIFE date, END_LIFE date
    -> LineOnAreaOverlayer_3 [AREA]
LineOnAreaOverlayer_3
    ATTR_ACCUM_MODE = Merge Incoming
    ATTR_CONFLICT_RES = Use Original
    CLEANING_TOLERANCE = Automatic
    DEAGGREGATE_INPUT = Yes
    OV_ATTR = _overlaps
    LINE -> TestFilter_4
TestFilter_4
    DEFAULT_VALUE = <UNFILTERED>
    TEST_LIST = "BOOL_OP,OR,COMPOSITE_TEST,""""""1"""""",TEST_CLAUSE,TEST @Value(_overlaps) != 0",All but 0

Bookmark: Nettoyer le réseau routier Urbis
Note: Filtrer les tunnels, les lignes de tram et les autoroutes
