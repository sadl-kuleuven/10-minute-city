FME workspace Modified_input.fmw

Parameters:
- DestDataset_SHAPEFILE =
- DestDataset_SHAPEFILE_10 =
- DestDataset_SHAPEFILE_102 =
- DestDataset_SHAPEFILE_103 =
- DestDataset_SHAPEFILE_104 =
- DestDataset_SHAPEFILE_105 =
- DestDataset_SHAPEFILE_106 =
- DestDataset_SHAPEFILE_107 =
- DestDataset_SHAPEFILE_108 =
- DestDataset_SHAPEFILE_109 =
- DestDataset_SHAPEFILE_11 =
- DestDataset_SHAPEFILE_110 =
- DestDataset_SHAPEFILE_111 =
- DestDataset_SHAPEFILE_112 =
- DestDataset_SHAPEFILE_113 =
- DestDataset_SHAPEFILE_114 =
- DestDataset_SHAPEFILE_115 =
- DestDataset_SHAPEFILE_116 =
- DestDataset_SHAPEFILE_117 =
- DestDataset_SHAPEFILE_118 =
- DestDataset_SHAPEFILE_119 =
- DestDataset_SHAPEFILE_12 =
- DestDataset_SHAPEFILE_120 =
- DestDataset_SHAPEFILE_121 =
- DestDataset_SHAPEFILE_122 =
- DestDataset_SHAPEFILE_123 =
- DestDataset_SHAPEFILE_124 =
- DestDataset_SHAPEFILE_125 =
- DestDataset_SHAPEFILE_126 =
- DestDataset_SHAPEFILE_127 =
- DestDataset_SHAPEFILE_128 =
- DestDataset_SHAPEFILE_129 =
- DestDataset_SHAPEFILE_13 =
- DestDataset_SHAPEFILE_130 =
- DestDataset_SHAPEFILE_131 =
- DestDataset_SHAPEFILE_132 =
- DestDataset_SHAPEFILE_133 =
- DestDataset_SHAPEFILE_134 =
- DestDataset_SHAPEFILE_135 =
- DestDataset_SHAPEFILE_136 =
- DestDataset_SHAPEFILE_137 =
- DestDataset_SHAPEFILE_138 =
- DestDataset_SHAPEFILE_139 =
- DestDataset_SHAPEFILE_14 =
- DestDataset_SHAPEFILE_140 =
- DestDataset_SHAPEFILE_141 =
- DestDataset_SHAPEFILE_142 =
- DestDataset_SHAPEFILE_143 =
- DestDataset_SHAPEFILE_144 =
- DestDataset_SHAPEFILE_15 =
- DestDataset_SHAPEFILE_16 =
- DestDataset_SHAPEFILE_17 =
- DestDataset_SHAPEFILE_18 =
- DestDataset_SHAPEFILE_19 =
- DestDataset_SHAPEFILE_2 =
- DestDataset_SHAPEFILE_20 =
- DestDataset_SHAPEFILE_21 =
- DestDataset_SHAPEFILE_22 =
- DestDataset_SHAPEFILE_23 =
- DestDataset_SHAPEFILE_24 =
- DestDataset_SHAPEFILE_25 =
- DestDataset_SHAPEFILE_26 =
- DestDataset_SHAPEFILE_27 =
- DestDataset_SHAPEFILE_28 =
- DestDataset_SHAPEFILE_29 =
- DestDataset_SHAPEFILE_3 =
- DestDataset_SHAPEFILE_4 =
- DestDataset_SHAPEFILE_5 =
- DestDataset_SHAPEFILE_6 =
- DestDataset_SHAPEFILE_7 =
- DestDataset_SHAPEFILE_8 =
- DestDataset_SHAPEFILE_9 =
- SourceDataset_SHAPEFILE =
- SourceDataset_SHAPEFILE_30 =
- SourceDataset_SHAPEFILE_31 =
- SourceDataset_SHAPEFILE_32 =
- SourceDataset_SHAPEFILE_33 =
- SourceDataset_SHAPEFILE_34 =
- SourceDataset_SHAPEFILE_35 =
- SourceDataset_SHAPEFILE_36 =
- SourceDataset_SHAPEFILE_37 =
- SourceDataset_SHAPEFILE_38 =
- SourceDataset_SHAPEFILE_39 =
- SourceDataset_SHAPEFILE_40 =
- SourceDataset_SHAPEFILE_41 =
- SourceDataset_SHAPEFILE_42 =
- SourceDataset_SHAPEFILE_43 =
- SourceDataset_SHAPEFILE_44 =
- SourceDataset_SHAPEFILE_45 =
- SourceDataset_SHAPEFILE_46 =
- SourceDataset_SHAPEFILE_47 =
- SourceDataset_SHAPEFILE_48 =
- SourceDataset_SHAPEFILE_49 =
- SourceDataset_SHAPEFILE_50 =
- SourceDataset_SHAPEFILE_51 =
- SourceDataset_SHAPEFILE_52 =
- SourceDataset_SHAPEFILE_53 =
- SourceDataset_SHAPEFILE_54 =
- SourceDataset_SHAPEFILE_55 =
- SourceDataset_SHAPEFILE_56 =
- SourceDataset_SHAPEFILE_57 =

Readers:
- SHAPEFILE_1: SHAPEFILE from $(SourceDataset_SHAPEFILE_31)
- SHAPEFILE_2: SHAPEFILE from $(SourceDataset_SHAPEFILE_38)
- SHAPEFILE_3: SHAPEFILE from $(SourceDataset_SHAPEFILE_39)
- SHAPEFILE_4: SHAPEFILE from $(SourceDataset_SHAPEFILE_49)
- SHAPEFILE_5: SHAPEFILE from $(SourceDataset_SHAPEFILE_50)
- SHAPEFILE_6: SHAPEFILE from $(SourceDataset_SHAPEFILE_51)
- SHAPEFILE_7: SHAPEFILE from $(SourceDataset_SHAPEFILE_32)
- SHAPEFILE_8: SHAPEFILE from $(SourceDataset_SHAPEFILE_33)
- SHAPEFILE_9: SHAPEFILE from $(SourceDataset_SHAPEFILE_34)
- SHAPEFILE_10: SHAPEFILE from $(SourceDataset_SHAPEFILE_35)
- SHAPEFILE_11: SHAPEFILE from $(SourceDataset_SHAPEFILE_52)
- SHAPEFILE_12: SHAPEFILE from $(SourceDataset_SHAPEFILE_53)
- SHAPEFILE_13: SHAPEFILE from $(SourceDataset_SHAPEFILE_54)
- SHAPEFILE_14: SHAPEFILE from $(SourceDataset_SHAPEFILE_55)
- SHAPEFILE_15: SHAPEFILE from $(SourceDataset_SHAPEFILE_56)
- SHAPEFILE_16: SHAPEFILE from $(SourceDataset_SHAPEFILE_36)
- SHAPEFILE_17: SHAPEFILE from $(SourceDataset_SHAPEFILE_30)
- SHAPEFILE_18: SHAPEFILE from $(SourceDataset_SHAPEFILE_57)
- SHAPEFILE_19: SHAPEFILE from $(SourceDataset_SHAPEFILE_37)
- SHAPEFILE_20: SHAPEFILE from $(SourceDataset_SHAPEFILE_40)
- SHAPEFILE_21: SHAPEFILE from $(SourceDataset_SHAPEFILE)
- SHAPEFILE_22: SHAPEFILE from $(SourceDataset_SHAPEFILE_46)
- SHAPEFILE_23: SHAPEFILE from $(SourceDataset_SHAPEFILE_47)
- SHAPEFILE_24: SHAPEFILE from $(SourceDataset_SHAPEFILE_48)
- SHAPEFILE_25: SHAPEFILE from $(SourceDataset_SHAPEFILE_41)
- SHAPEFILE_26: SHAPEFILE from $(SourceDataset_SHAPEFILE_42)
- SHAPEFILE_27: SHAPEFILE from $(SourceDataset_SHAPEFILE_43)
- SHAPEFILE_28: SHAPEFILE from $(SourceDataset_SHAPEFILE_44)
- SHAPEFILE_29: SHAPEFILE from $(SourceDataset_SHAPEFILE_45)

Writers:
- SHAPEFILE_30: SHAPEFILE to $(DestDataset_SHAPEFILE)
- SHAPEFILE_31: SHAPEFILE to $(DestDataset_SHAPEFILE_2)
- SHAPEFILE_32: SHAPEFILE to $(DestDataset_SHAPEFILE_19)
- SHAPEFILE_33: SHAPEFILE to $(DestDataset_SHAPEFILE_3)
- SHAPEFILE_34: SHAPEFILE to $(DestDataset_SHAPEFILE_4)
- SHAPEFILE_35: SHAPEFILE to $(DestDataset_SHAPEFILE_5)
- SHAPEFILE_36: SHAPEFILE to $(DestDataset_SHAPEFILE_6)
- SHAPEFILE_37: SHAPEFILE to $(DestDataset_SHAPEFILE_21)
- SHAPEFILE_38: SHAPEFILE to $(DestDataset_SHAPEFILE_7)
- SHAPEFILE_39: SHAPEFILE to $(DestDataset_SHAPEFILE_8)
- SHAPEFILE_40: SHAPEFILE to $(DestDataset_SHAPEFILE_9)
- SHAPEFILE_41: SHAPEFILE to $(DestDataset_SHAPEFILE_136)
- SHAPEFILE_42: SHAPEFILE to $(DestDataset_SHAPEFILE_104)
- SHAPEFILE_43: SHAPEFILE to $(DestDataset_SHAPEFILE_137)
- SHAPEFILE_44: SHAPEFILE to $(DestDataset_SHAPEFILE_138)
- SHAPEFILE_45: SHAPEFILE to $(DestDataset_SHAPEFILE_22)
- SHAPEFILE_46: SHAPEFILE to $(DestDataset_SHAPEFILE_13)
- SHAPEFILE_47: SHAPEFILE to $(DestDataset_SHAPEFILE_15)
- SHAPEFILE_48: SHAPEFILE to $(DestDataset_SHAPEFILE_112)
- SHAPEFILE_49: SHAPEFILE to $(DestDataset_SHAPEFILE_124)
- SHAPEFILE_50: SHAPEFILE to $(DestDataset_SHAPEFILE_23)
- SHAPEFILE_51: SHAPEFILE to $(DestDataset_SHAPEFILE_139)
- SHAPEFILE_52: SHAPEFILE to $(DestDataset_SHAPEFILE_24)
- SHAPEFILE_53: SHAPEFILE to $(DestDataset_SHAPEFILE_140)
- SHAPEFILE_54: SHAPEFILE to $(DestDataset_SHAPEFILE_108)
- SHAPEFILE_55: SHAPEFILE to $(DestDataset_SHAPEFILE_116)
- SHAPEFILE_56: SHAPEFILE to $(DestDataset_SHAPEFILE_20)
- SHAPEFILE_57: SHAPEFILE to $(DestDataset_SHAPEFILE_141)
- SHAPEFILE_58: SHAPEFILE to $(DestDataset_SHAPEFILE_142)
- SHAPEFILE_59: SHAPEFILE to $(DestDataset_SHAPEFILE_143)
- SHAPEFILE_60: SHAPEFILE to $(DestDataset_SHAPEFILE_25)
- SHAPEFILE_61: SHAPEFILE to $(DestDataset_SHAPEFILE_11)
- SHAPEFILE_62: SHAPEFILE to $(DestDataset_SHAPEFILE_144)
- SHAPEFILE_63: SHAPEFILE to $(DestDataset_SHAPEFILE_17)
- SHAPEFILE_64: SHAPEFILE to $(DestDataset_SHAPEFILE_102)
- SHAPEFILE_65: SHAPEFILE to $(DestDataset_SHAPEFILE_106)
- SHAPEFILE_66: SHAPEFILE to $(DestDataset_SHAPEFILE_110)
- SHAPEFILE_67: SHAPEFILE to $(DestDataset_SHAPEFILE_114)
- SHAPEFILE_68: SHAPEFILE to $(DestDataset_SHAPEFILE_118)
- SHAPEFILE_69: SHAPEFILE to $(DestDataset_SHAPEFILE_120)
- SHAPEFILE_70: SHAPEFILE to $(DestDataset_SHAPEFILE_122)
- SHAPEFILE_71: SHAPEFILE to $(DestDataset_SHAPEFILE_126)
- SHAPEFILE_72: SHAPEFILE to $(DestDataset_SHAPEFILE_26)
- SHAPEFILE_73: SHAPEFILE to $(DestDataset_SHAPEFILE_27)
- SHAPEFILE_74: SHAPEFILE to $(DestDataset_SHAPEFILE_28)
- SHAPEFILE_75: SHAPEFILE to $(DestDataset_SHAPEFILE_29)
- SHAPEFILE_76: SHAPEFILE to $(DestDataset_SHAPEFILE_10)
- SHAPEFILE_77: SHAPEFILE to $(DestDataset_SHAPEFILE_12)
- SHAPEFILE_78: SHAPEFILE to $(DestDataset_SHAPEFILE_14)
- SHAPEFILE_79: SHAPEFILE to $(DestDataset_SHAPEFILE_16)
- SHAPEFILE_80: SHAPEFILE to $(DestDataset_SHAPEFILE_18)
- SHAPEFILE_81: SHAPEFILE to $(DestDataset_SHAPEFILE_103)
- SHAPEFILE_82: SHAPEFILE to $(DestDataset_SHAPEFILE_105)
- SHAPEFILE_83: SHAPEFILE to $(DestDataset_SHAPEFILE_107)
- SHAPEFILE_84: SHAPEFILE to $(DestDataset_SHAPEFILE_109)
- SHAPEFILE_85: SHAPEFILE to $(DestDataset_SHAPEFILE_111)
- SHAPEFILE_86: SHAPEFILE to $(DestDataset_SHAPEFILE_113)
- SHAPEFILE_87: SHAPEFILE to $(DestDataset_SHAPEFILE_115)
- SHAPEFILE_88: SHAPEFILE to $(DestDataset_SHAPEFILE_117)
- SHAPEFILE_89: SHAPEFILE to $(DestDataset_SHAPEFILE_119)
- SHAPEFILE_90: SHAPEFILE to $(DestDataset_SHAPEFILE_121)
- SHAPEFILE_91: SHAPEFILE to $(DestDataset_SHAPEFILE_123)
- SHAPEFILE_92: SHAPEFILE to $(DestDataset_SHAPEFILE_125)
- SHAPEFILE_93: SHAPEFILE to $(DestDataset_SHAPEFILE_127)
- SHAPEFILE_94: SHAPEFILE to $(DestDataset_SHAPEFILE_128)
- SHAPEFILE_95: SHAPEFILE to $(DestDataset_SHAPEFILE_129)
- SHAPEFILE_96: SHAPEFILE to $(DestDataset_SHAPEFILE_130)
- SHAPEFILE_97: SHAPEFILE to $(DestDataset_SHAPEFILE_131)
- SHAPEFILE_98: SHAPEFILE to $(DestDataset_SHAPEFILE_132)
- SHAPEFILE_99: SHAPEFILE to $(DestDataset_SHAPEFILE_133)
- SHAPEFILE_100: SHAPEFILE to $(DestDataset_SHAPEFILE_134)
- SHAPEFILE_101: SHAPEFILE to $(DestDataset_SHAPEFILE_135)

soutien_scolaire (reader SHAPEFILE_12)
    attributes: ID_FICHE number(31,15), LIEN varchar(254), NOM varchar(254), AUTRE_NOM varchar(254), SERV_INT varchar(254), RUE varchar(254), NUMERO varchar(254), BOITE number(31,15), CP number(31,15), COMMUNE varchar(254), REM_ADR varchar(254), QUARTIER varchar(254), QUARTIER_C number(31,15), SECT_STAT varchar(254), SECT_STAT_ varchar(254), TEL varchar(254), FAX varchar(254), MAIL varchar(254), SITE varchar(254), AUTRE_SITE varchar(254), SITE_AS varchar(254), BENEFICIAI varchar(254), ZONE_ACTIO varchar(254), LANGUE varchar(254), INTERPRET varchar(254), TYPE varchar(254), CONTACT varchar(254), QUAND varchar(254), REVUE varchar(254), REMARQUES varchar(254),
      AGREMENT varchar(254), AUTRES_AGR varchar(254), STATUT_JUR varchar(254), NUM_ENTREP number(31,15), PUB_MONITE varchar(254), STATUT_LIN varchar(254), ANCIEN_NOM varchar(254), CREE_PAR varchar(254), FAIT_PARTI varchar(254), ANTENNE_DE varchar(254), SECTEUR varchar(254), MAJ date, LEGENDE varchar(254), ADRESSE varchar(254), PERIMETRE number(11,0), ID number(11,0)
    -> TestFilter_14
TestFilter_14
    DEFAULT_VALUE = <UNFILTERED>
    TEST_LIST:
      "BOOL_OP,OR,COMPOSITE_TEST,""""""1 OR 2"""""",TEST_CLAUSE,TEST @Value(LEGENDE) = ecole des devoirs
      TEST @Value(LEGENDE) = ecole des devoirs + médiation scolaire",ecole de devoirs
    ecole de devoirs -> ecole de devoirs (writer SHAPEFILE_73)
ecole de devoirs (writer SHAPEFILE_73)
    attributes: ID_FICHE number(31,15), LIEN varchar(254), NOM varchar(254), AUTRE_NOM varchar(254), SERV_INT varchar(254), RUE varchar(254), NUMERO varchar(254), BOITE number(31,15), CP number(31,15), COMMUNE varchar(254), REM_ADR varchar(254), QUARTIER varchar(254), QUARTIER_C number(31,15), SECT_STAT varchar(254), SECT_STAT_ varchar(254), TEL varchar(254), FAX varchar(254), MAIL varchar(254), SITE varchar(254), AUTRE_SITE varchar(254), SITE_AS varchar(254), BENEFICIAI varchar(254), ZONE_ACTIO varchar(254), LANGUE varchar(254), INTERPRET varchar(254), TYPE varchar(254), CONTACT varchar(254), QUAND varchar(254), REVUE varchar(254), REMARQUES varchar(254),
      AGREMENT varchar(254), AUTRES_AGR varchar(254), STATUT_JUR varchar(254), NUM_ENTREP number(31,15), PUB_MONITE varchar(254), STATUT_LIN varchar(254), ANCIEN_NOM varchar(254), CREE_PAR varchar(254), FAIT_PARTI varchar(254), ANTENNE_DE varchar(254), SECTEUR varchar(254), MAJ date, LEGENDE varchar(254), ADRESSE varchar(254), PERIMETRE number(11,0), ID number(11,0)
2020_be_brat_inventaire_ev_publics (reader SHAPEFILE_18)
    attributes: pk number(20,0), gid number(11,0), pgs_id number(11,0), name_f varchar(254), name_n varchar(254), name_e varchar(254), surface number(31,15), vegetation number(11,0), permeabili long, type varchar(254), subtype varchar(254), accessibil long, on_roof long, temporary long, assignment varchar(254), encodage_f long, géometrie long, géometr_1 long, potentiel long, SUBTYPE_2 varchar(50)
    -> TestFilter_26
TestFilter_26
    DEFAULT_VALUE = <UNFILTERED>
    TEST_LIST:
      "BOOL_OP,AND,COMPOSITE_TEST,""""""1 AND 2"""""",TEST_CLAUSE,TEST @Value(SUBTYPE_2) = EV_QUALI
      TEST @Value(surface) < 5000",Micro qualitatif,"BOOL_OP,AND,COMPOSITE_TEST,""""""1 AND 2 AND 3"""""",TEST_CLAUSE,TEST @Value(SUBTYPE_2) = EV_QUALI
      TEST @Value(surface) >= 5000
      TEST @Value(surface) < 30000",Meso qualitatif,"BOOL_OP,AND,COMPOSITE_TEST,""""""1 AND 2"""""",TEST_CLAUSE,TEST @Value(SUBTYPE_2) = EV_QUALI
      TEST @Value(surface) >= 30000",Macro qualitatif
    Micro qualitatif -> Micro qualitatif (writer SHAPEFILE_89)
    Meso qualitatif -> Meso qualitatif (writer SHAPEFILE_89)
    Macro qualitatif -> Macro qualitatif (writer SHAPEFILE_89)
Micro qualitatif (writer SHAPEFILE_89)
    attributes: pk number(20,0), gid number(11,0), pgs_id number(11,0), name_f varchar(254), name_n varchar(254), name_e varchar(254), surface number(31,15), vegetation number(11,0), permeabili long, type varchar(254), subtype varchar(254), accessibil long, on_roof long, temporary long, assignment varchar(254), encodage_f long, géometrie long, géometr_1 long, potentiel long, SUBTYPE_2 varchar(50)
Meso qualitatif (writer SHAPEFILE_89)
    attributes: pk number(20,0), gid number(11,0), pgs_id number(11,0), name_f varchar(254), name_n varchar(254), name_e varchar(254), surface number(31,15), vegetation number(11,0), permeabili long, type varchar(254), subtype varchar(254), accessibil long, on_roof long, temporary long, assignment varchar(254), encodage_f long, géometrie long, géometr_1 long, potentiel long, SUBTYPE_2 varchar(50)
Macro qualitatif (writer SHAPEFILE_89)
    attributes: pk number(20,0), gid number(11,0), pgs_id number(11,0), name_f varchar(254), name_n varchar(254), name_e varchar(254), surface number(31,15), vegetation number(11,0), permeabili long, type varchar(254), subtype varchar(254), accessibil long, on_roof long, temporary long, assignment varchar(254), encodage_f long, géometrie long, géometr_1 long, potentiel long, SUBTYPE_2 varchar(50)
bibliotheques (reader SHAPEFILE_14)
    attributes: DÃ©nomin varchar(254), Adresse varchar(254), CP varchar(254), TÃ©lÃ© varchar(254), Langue varchar(254), C_TypeEcol varchar(254), GESTION varchar(50), PERIMETRE number(11,0), ID number(11,0)
    -> TestFilter_17
TestFilter_17
    DEFAULT_VALUE = <UNFILTERED>
    TEST_LIST:
      "BOOL_OP,AND,COMPOSITE_TEST,""""""1 AND 2"""""",TEST_CLAUSE,TEST @Value(C_TypeEcol) = Bibliothèque
      TEST @Value(Langue) = F",FR,"BOOL_OP,AND,COMPOSITE_TEST,""""""1 AND 2"""""",TEST_CLAUSE,TEST @Value(C_TypeEcol) = Bibliothèque
      TEST @Value(Langue) = N",NL
    FR -> FR (writer SHAPEFILE_76)
    NL -> NL (writer SHAPEFILE_77)
FR (writer SHAPEFILE_76)
    attributes: DÃ©nomin varchar(254), Adresse varchar(254), CP varchar(254), TÃ©lÃ© varchar(254), Langue varchar(254), C_TypeEcol varchar(254), GESTION varchar(50), PERIMETRE number(11,0), ID number(11,0)
NL (writer SHAPEFILE_77)
    attributes: DÃ©nomin varchar(254), Adresse varchar(254), CP varchar(254), TÃ©lÃ© varchar(254), Langue varchar(254), C_TypeEcol varchar(254), GESTION varchar(50), PERIMETRE number(11,0), ID number(11,0)
instruction (reader SHAPEFILE_17)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
    -> TestFilter_18
    -> TestFilter_20
    -> TestFilter_23
    -> TestFilter_24
    -> TestFilter_25
TestFilter_18
    DEFAULT_VALUE = <UNFILTERED>
    TEST_LIST:
      "BOOL_OP,AND,COMPOSITE_TEST,""""""1 AND 2"""""",TEST_CLAUSE,TEST @Value(LEGENDE) = SAHR
      TEST @Value(LANGUE) = FR",FR_SAHR,"BOOL_OP,AND,COMPOSITE_TEST,""""""1 AND 2"""""",TEST_CLAUSE,TEST @Value(LEGENDE) = SAHR
      TEST @Value(LANGUE) = NL",NL_SAHR
    FR_SAHR -> FR (writer SHAPEFILE_78)
    NL_SAHR -> NL (writer SHAPEFILE_79)
FR (writer SHAPEFILE_78)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
NL (writer SHAPEFILE_79)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
TestFilter_20
    DEFAULT_VALUE = <UNFILTERED>
    TEST_LIST:
      "BOOL_OP,AND,COMPOSITE_TEST,""""""1 AND 2 AND 3"""""",TEST_CLAUSE,TEST @Value(TYPE) = ordinaire
      TEST @Value(NIVEAU) = maternel
      TEST @Value(LANGUE) = FR",FR_ecole maternel ordinair,"BOOL_OP,AND,COMPOSITE_TEST,""""""1 AND 2 AND 3"""""",TEST_CLAUSE,TEST @Value(TYPE) = ordinaire
      TEST @Value(NIVEAU) = maternel
      TEST @Value(LANGUE) = NL",NL_ecole maternel ordinair
    FR_ecole maternel ordinair -> FR (writer SHAPEFILE_82)
    NL_ecole maternel ordinair -> NL (writer SHAPEFILE_83)
FR (writer SHAPEFILE_82)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
NL (writer SHAPEFILE_83)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
TestFilter_23
    DEFAULT_VALUE = <UNFILTERED>
    TEST_LIST:
      "BOOL_OP,AND,COMPOSITE_TEST,""""""1 AND 2 AND 3"""""",TEST_CLAUSE,TEST @Value(TYPE) = ordinaire
      TEST @Value(NIVEAU) = primaire
      TEST @Value(LANGUE) = FR",FR_ecole primaire ordinair,"BOOL_OP,AND,COMPOSITE_TEST,""""""1 AND 2 AND 3"""""",TEST_CLAUSE,TEST @Value(TYPE) = ordinaire
      TEST @Value(NIVEAU) = primaire
      TEST @Value(LANGUE) = NL",NL_ecole primaire ordinair
    FR_ecole primaire ordinair -> FR (writer SHAPEFILE_84)
    NL_ecole primaire ordinair -> NL (writer SHAPEFILE_85)
FR (writer SHAPEFILE_84)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
NL (writer SHAPEFILE_85)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
TestFilter_24
    DEFAULT_VALUE = <UNFILTERED>
    TEST_LIST:
      "BOOL_OP,AND,COMPOSITE_TEST,""""""1 AND 2 AND 3"""""",TEST_CLAUSE,TEST @Value(TYPE) = ordinaire
      TEST @Value(NIVEAU) = secondaire
      TEST @Value(LANGUE) = FR",FR_ecole secondaire ordinair,"BOOL_OP,AND,COMPOSITE_TEST,""""""1 AND 2 AND 3"""""",TEST_CLAUSE,TEST @Value(TYPE) = ordinaire
      TEST @Value(NIVEAU) = secondaire
      TEST @Value(LANGUE) = NL",NL_ecole secondaire ordinair
    FR_ecole secondaire ordinair -> FR (writer SHAPEFILE_86)
    NL_ecole secondaire ordinair -> NL (writer SHAPEFILE_87)
FR (writer SHAPEFILE_86)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
NL (writer SHAPEFILE_87)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
TestFilter_25
    DEFAULT_VALUE = <UNFILTERED>
    TEST_LIST:
      "BOOL_OP,OR,COMPOSITE_TEST,""""""1 OR 2"""""",TEST_CLAUSE,TEST @Value(NIVEAU) = promotion sociale
      TEST @Value(NIVEAU) = volwasseneonderwijs",promotion sociale/volwassenenonderwijs
    promotion sociale/volwassenenonderwijs -> promotion sociale _ volwassenenonderwijs (writer SHAPEFILE_88)
promotion sociale _ volwassenenonderwijs (writer SHAPEFILE_88)
    attributes: NOM varchar(254), ADRESSE varchar(254), CP double, LOCALITE varchar(254), LEGENDE varchar(254), Remarques varchar(254), RESEAU varchar(254), NIVEAU varchar(254), TYPE varchar(254), SOURCE varchar(254), TERRITOIRE varchar(254), X double, Y double, PERIMETRE number(11,0), ID number(11,0), SUP varchar(50), LANGUE varchar(50), GRP_SCOL varchar(100), SURFACE varchar(50), SURF varchar(50), TELEPHONE varchar(13), NB_ELEVES long, NB_EMPL short
centres_sportifs (reader SHAPEFILE_19)
    attributes: ID short, PERIMETRE short, name varchar(51), category varchar(22), website varchar(118), city varchar(27), street_nam varchar(40), street_num varchar(8), address varchar(44), source varchar(33), infrastruc varchar(250), omnisport varchar(3), salle_poly varchar(3), petanque varchar(3), foot varchar(3), mini_foot varchar(3), basket varchar(3), tennis varchar(3), FitSpinMus varchar(3), escalade varchar(3), gymnase varchar(3), danse_aero varchar(3), ArtMarComb varchar(3), padel varchar(3), squash varchar(3), athletisme varchar(3), badminton varchar(3), hockey varchar(3), tennis_tab varchar(3), Foot_ameri varchar(3),
      rugby varchar(3), escrime varchar(3), volley varchar(3), handball varchar(3), Beach_Voll varchar(3), tir_arc varchar(3)
    -> TestFilter_27
    -> TestFilter_28
    -> TestFilter_29
    -> TestFilter_30
TestFilter_27
    DEFAULT_VALUE = <UNFILTERED>
    TEST_LIST = "BOOL_OP,OR,COMPOSITE_TEST,""""""1"""""",TEST_CLAUSE,TEST @Value(omnisport) = Oui",Hall Omnisport
    Hall Omnisport -> hall omnisport (writer SHAPEFILE_90)
hall omnisport (writer SHAPEFILE_90)
    attributes: ID short, PERIMETRE short, name varchar(51), category varchar(22), website varchar(118), city varchar(27), street_nam varchar(40), street_num varchar(8), address varchar(44), source varchar(33), infrastruc varchar(250), omnisport varchar(3), salle_poly varchar(3), petanque varchar(3), foot varchar(3), mini_foot varchar(3), basket varchar(3), tennis varchar(3), FitSpinMus varchar(3), escalade varchar(3), gymnase varchar(3), danse_aero varchar(3), ArtMarComb varchar(3), padel varchar(3), squash varchar(3), athletisme varchar(3), badminton varchar(3), hockey varchar(3), tennis_tab varchar(3), Foot_ameri varchar(3),
      rugby varchar(3), escrime varchar(3), volley varchar(3), handball varchar(3), Beach_Voll varchar(3), tir_arc varchar(3)
TestFilter_28
    DEFAULT_VALUE = <UNFILTERED>
    TEST_LIST:
      "BOOL_OP,OR,COMPOSITE_TEST,""""""1 OR 2 OR 3 OR 4 OR 5 OR 6 OR 7 OR 8"""""",TEST_CLAUSE,TEST @Value(foot) = Oui
      TEST @Value(tennis) = Oui
      TEST @Value(athletisme) = Oui
      TEST @Value(hockey) = Oui
      TEST @Value(petanque) = Oui
      TEST @Value(rugby) = Oui
      TEST @Value(basket) = Oui
      TEST @Value(badminton) = Oui",Terrains de sport spécifiques
    Terrains de sport spécifiques -> Terrains de sport spécifiques (writer SHAPEFILE_92)
Terrains de sport spécifiques (writer SHAPEFILE_92)
    attributes: ID short, PERIMETRE short, name varchar(51), category varchar(22), website varchar(118), city varchar(27), street_nam varchar(40), street_num varchar(8), address varchar(44), source varchar(33), infrastruc varchar(250), omnisport varchar(3), salle_poly varchar(3), petanque varchar(3), foot varchar(3), mini_foot varchar(3), basket varchar(3), tennis varchar(3), FitSpinMus varchar(3), escalade varchar(3), gymnase varchar(3), danse_aero varchar(3), ArtMarComb varchar(3), padel varchar(3), squash varchar(3), athletisme varchar(3), badminton varchar(3), hockey varchar(3), tennis_tab varchar(3), Foot_ameri varchar(3),
      rugby varchar(3), escrime varchar(3), volley varchar(3), handball varchar(3), Beach_Voll varchar(3), tir_arc varchar(3)
TestFilter_29
    DEFAULT_VALUE = <UNFILTERED>
    TEST_LIST = "BOOL_OP,OR,COMPOSITE_TEST,""""""1"""""",TEST_CLAUSE,TEST @Value(salle_poly) = Oui",Salle polyvalente sportive
    Salle polyvalente sportive -> salle polyvalente sportive (writer SHAPEFILE_90)
salle polyvalente sportive (writer SHAPEFILE_90)
    attributes: ID short, PERIMETRE short, name varchar(51), category varchar(22), website varchar(118), city varchar(27), street_nam varchar(40), street_num varchar(8), address varchar(44), source varchar(33), infrastruc varchar(250), omnisport varchar(3), salle_poly varchar(3), petanque varchar(3), foot varchar(3), mini_foot varchar(3), basket varchar(3), tennis varchar(3), FitSpinMus varchar(3), escalade varchar(3), gymnase varchar(3), danse_aero varchar(3), ArtMarComb varchar(3), padel varchar(3), squash varchar(3), athletisme varchar(3), badminton varchar(3), hockey varchar(3), tennis_tab varchar(3), Foot_ameri varchar(3),
      rugby varchar(3), escrime varchar(3), volley varchar(3), handball varchar(3), Beach_Voll varchar(3), tir_arc varchar(3)
TestFilter_30
    DEFAULT_VALUE = <UNFILTERED>
    TEST_LIST:
      "BOOL_OP,OR,COMPOSITE_TEST,""""""1 OR 2 OR 3 OR 4 OR 5"""""",TEST_CLAUSE,TEST @Value(ArtMarComb) = Oui
      TEST @Value(gymnase) = Oui
      TEST @Value(FitSpinMus) = Oui
      TEST @Value(squash) = Oui
      TEST @Value(escalade) = Oui",Salles sportives spécifiques
    Salles sportives spécifiques -> Salles sportives spécifiques (writer SHAPEFILE_91)
Salles sportives spécifiques (writer SHAPEFILE_91)
    attributes: ID short, PERIMETRE short, name varchar(51), category varchar(22), website varchar(118), city varchar(27), street_nam varchar(40), street_num varchar(8), address varchar(44), source varchar(33), infrastruc varchar(250), omnisport varchar(3), salle_poly varchar(3), petanque varchar(3), foot varchar(3), mini_foot varchar(3), basket varchar(3), tennis varchar(3), FitSpinMus varchar(3), escalade varchar(3), gymnase varchar(3), danse_aero varchar(3), ArtMarComb varchar(3), padel varchar(3), squash varchar(3), athletisme varchar(3), badminton varchar(3), hockey varchar(3), tennis_tab varchar(3), Foot_ameri varchar(3),
      rugby varchar(3), escrime varchar(3), volley varchar(3), handball varchar(3), Beach_Voll varchar(3), tir_arc varchar(3)
Note: 2021
plaines_jeux_ibge_modifie (reader SHAPEFILE_10)
    attributes: gid varchar(254), id_airesde varchar(254), nom varchar(254), adresse_tx varchar(254), adresse_zi varchar(254), age varchar(254), leeftijd varchar(254), descriptio varchar(254), descriptie varchar(254), heure_ouve varchar(254), openingsti varchar(254), ev_type varchar(254), type varchar(254), soort varchar(254), commune varchar(254), gemeente varchar(254), MODIF varchar(50), gestion varchar(50), PERIMETRE number(11,0), ID number(11,0)
    -> TestFilter_10
TestFilter_10
    DEFAULT_VALUE = <UNFILTERED>
    TEST_LIST:
      "BOOL_OP,OR,COMPOSITE_TEST,""""""1 OR 2"""""",TEST_CLAUSE,TEST @Value(type) = Terrain de sport outdoor
      TEST @Value(type) = Agoraspace",Terrain de sport + agoraspace,"BOOL_OP,OR,COMPOSITE_TEST,""""""1 OR 2"""""",TEST_CLAUSE,TEST @Value(type) = Parcours santé
      TEST @Value(type) = Fitness",Parcours santé + fitness,"BOOL_OP,OR,COMPOSITE_TEST,""""""1"""""",TEST_CLAUSE,TEST @Value(type) = Ping Pong",Ping Pong,"BOOL_OP,OR,COMPOSITE_TEST,""""""1"""""",TEST_CLAUSE,TEST @Value(type) = BMX",BMX,"BOOL_OP,OR,COMPOSITE_TEST,""""""1"""""",TEST_CLAUSE,TEST @Value(type) = Pétanque",Pétanque,"BOOL_OP,OR,COMPOSITE_TEST,""""""1"""""",TEST_CLAUSE,TEST @Value(type) = Skatepark",Skatepark
    Terrain de sport + agoraspace -> Terrain de sport + agoraspace (writer SHAPEFILE_52)
    Parcours santé + fitness -> Parcours santé + fitness (writer SHAPEFILE_53)
    Ping Pong -> Ping Pong (writer SHAPEFILE_54)
    BMX -> BMX (writer SHAPEFILE_55)
    Pétanque -> Pétanque (writer SHAPEFILE_56)
    Skatepark -> Skatepark (writer SHAPEFILE_57)
Note: 2024
Note: 2040
Terrain de sport + agoraspace (writer SHAPEFILE_52)
    attributes: gid varchar(254), id_airesde varchar(254), nom varchar(254), adresse_tx varchar(254), adresse_zi varchar(254), age varchar(254), leeftijd varchar(254), descriptio varchar(254), descriptie varchar(254), heure_ouve varchar(254), openingsti varchar(254), ev_type varchar(254), type varchar(254), soort varchar(254), commune varchar(254), gemeente varchar(254), MODIF varchar(50), gestion varchar(50), PERIMETRE number(11,0), ID number(11,0)
Parcours santé + fitness (writer SHAPEFILE_53)
    attributes: gid varchar(254), id_airesde varchar(254), nom varchar(254), adresse_tx varchar(254), adresse_zi varchar(254), age varchar(254), leeftijd varchar(254), descriptio varchar(254), descriptie varchar(254), heure_ouve varchar(254), openingsti varchar(254), ev_type varchar(254), type varchar(254), soort varchar(254), commune varchar(254), gemeente varchar(254), MODIF varchar(50), gestion varchar(50), PERIMETRE number(11,0), ID number(11,0)
Ping Pong (writer SHAPEFILE_54)
    attributes: gid varchar(254), id_airesde varchar(254), nom varchar(254), adresse_tx varchar(254), adresse_zi varchar(254), age varchar(254), leeftijd varchar(254), descriptio varchar(254), descriptie varchar(254), heure_ouve varchar(254), openingsti varchar(254), ev_type varchar(254), type varchar(254), soort varchar(254), commune varchar(254), gemeente varchar(254), MODIF varchar(50), gestion varchar(50), PERIMETRE number(11,0), ID number(11,0)
BMX (writer SHAPEFILE_55)
    attributes: gid varchar(254), id_airesde varchar(254), nom varchar(254), adresse_tx varchar(254), adresse_zi varchar(254), age varchar(254), leeftijd varchar(254), descriptio varchar(254), descriptie varchar(254), heure_ouve varchar(254), openingsti varchar(254), ev_type varchar(254), type varchar(254), soort varchar(254), commune varchar(254), gemeente varchar(254), MODIF varchar(50), gestion varchar(50), PERIMETRE number(11,0), ID number(11,0)
Pétanque (writer SHAPEFILE_56)
    attributes: gid varchar(254), id_airesde varchar(254), nom varchar(254), adresse_tx varchar(254), adresse_zi varchar(254), age varchar(254), leeftijd varchar(254), descriptio varchar(254), descriptie varchar(254), heure_ouve varchar(254), openingsti varchar(254), ev_type varchar(254), type varchar(254), soort varchar(254), commune varchar(254), gemeente varchar(254), MODIF varchar(50), gestion varchar(50), PERIMETRE number(11,0), ID number(11,0)
Skatepark (writer SHAPEFILE_57)
    attributes: gid varchar(254), id_airesde varchar(254), nom varchar(254), adresse_tx varchar(254), adresse_zi varchar(254), age varchar(254), leeftijd varchar(254), descriptio varchar(254), descriptie varchar(254), heure_ouve varchar(254), openingsti varchar(254), ev_type varchar(254), type varchar(254), soort varchar(254), commune varchar(254), gemeente varchar(254), MODIF varchar(50), gestion varchar(50), PERIMETRE number(11,0), ID number(11,0)
Foot (writer SHAPEFILE_90)
    attributes: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
Tennis (writer SHAPEFILE_90)
    attributes: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
Athlétisme (writer SHAPEFILE_90)
    attributes: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
Hockey (writer SHAPEFILE_90)
    attributes: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
Petanque (writer SHAPEFILE_90)
    attributes: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
Rugby (writer SHAPEFILE_90)
    attributes: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
Basket (writer SHAPEFILE_90)
    attributes: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
Badminton (writer SHAPEFILE_90)
    attributes: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
Artsmartiaux (writer SHAPEFILE_90)
    attributes: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
Gymnase (writer SHAPEFILE_90)
    attributes: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
Fitness (writer SHAPEFILE_90)
    attributes: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
Squash (writer SHAPEFILE_90)
    attributes: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
Escalade (writer SHAPEFILE_90)
    attributes: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

Bookmark: 09 Sante
Note: Sante - Query - part 1: / "SECTEUR_2" = 'URGENCES' / Sante - Query - part 2: / ("SECTEUR_1" = 'MED' OR "SECTEUR_1" = 'MED + PSY') / AND"LEGENDE" = 'Postes de garde médecine' / OR ("LEGENDE" = 'médecine globale et intégrée OR "LEGENDE" = 'médecine globale et intégrée + consultations psy' OR "LEGENDE" =' médecine globale et intégrée + planning familial + service de santé mentale' OR "LEGENDE" = 'médecine globale et intégrée + service de santé mentale') / Sante - Query - part 3: / ("SECTEUR_1" = 'MED' OR "SECTEUR_1" = 'MED + PSY') / AND ("LEGENDE" = 'médecine globale et intégrée + planning familial + service de santé mentale' OR "LEGENDE" = 'planning familial + consultations psy' OR "LEGENDE" = 'hôpitaux + planning familial + consultations psy')
sante (reader SHAPEFILE_9)
    attributes: PERIMETRE number(11,0), ID_FICHE double, LIEN varchar(254), LEGENDE varchar(254), NOM varchar(254), AUTRE_NOM varchar(254), SERV_INT varchar(254), RUE varchar(254), NUMERO double, BOITE double, CP double, COMMUNE varchar(254), REM_ADR varchar(254), QUARTIER varchar(254), QUARTIER_C double, SECT_STAT varchar(254), SECT_STAT_ varchar(254), SITE varchar(254), AUTRE_SITE varchar(254), SITE_AS varchar(254), ZONE_ACTIO varchar(254), LANGUE varchar(254), INTERPRET varchar(254), TYPE varchar(254), QUAND varchar(254), REVUE varchar(254), AGREMENT varchar(254), AUTRES_AGR varchar(254), STATUT_JUR varchar(254), NUM_ENTREP double,
      PUB_MONITE varchar(254), STATUT_LIN varchar(254), ANCIEN_NOM varchar(254), CREE_PAR varchar(254), FAIT_PARTI varchar(254), ANTENNE_DE varchar(254), ORGANISATI varchar(254), SECTEUR varchar(254), MAJ date, ADRESSE varchar(254), SECTEUR_1 varchar(50), ID number(11,0), NAME_FRE varchar(60), SECTEUR_2 varchar(10)
    -> TestFilter_9
    -> TestFilter_21
    -> TestFilter_22
TestFilter_9
    DEFAULT_VALUE = <UNFILTERED>
    TEST_LIST = "BOOL_OP,OR,COMPOSITE_TEST,""""""1"""""",TEST_CLAUSE,TEST @Value(SECTEUR_2) = URGENCES",URGENCES
    URGENCES -> Urgences (writer SHAPEFILE_51)
Urgences (writer SHAPEFILE_51)
    attributes: PERIMETRE number(11,0), ID_FICHE double, LIEN varchar(254), LEGENDE varchar(254), NOM varchar(254), AUTRE_NOM varchar(254), SERV_INT varchar(254), RUE varchar(254), NUMERO double, BOITE double, CP double, COMMUNE varchar(254), REM_ADR varchar(254), QUARTIER varchar(254), QUARTIER_C double, SECT_STAT varchar(254), SECT_STAT_ varchar(254), SITE varchar(254), AUTRE_SITE varchar(254), SITE_AS varchar(254), ZONE_ACTIO varchar(254), LANGUE varchar(254), INTERPRET varchar(254), TYPE varchar(254), QUAND varchar(254), REVUE varchar(254), AGREMENT varchar(254), AUTRES_AGR varchar(254), STATUT_JUR varchar(254), NUM_ENTREP double,
      PUB_MONITE varchar(254), STATUT_LIN varchar(254), ANCIEN_NOM varchar(254), CREE_PAR varchar(254), FAIT_PARTI varchar(254), ANTENNE_DE varchar(254), ORGANISATI varchar(254), SECTEUR varchar(254), MAJ date, ADRESSE varchar(254), SECTEUR_1 varchar(50), ID number(11,0), NAME_FRE varchar(60), SECTEUR_2 varchar(10)
TestFilter_21
    DEFAULT_VALUE = <UNFILTERED>
    TEST_LIST:
      "BOOL_OP,COMPOSITE,COMPOSITE_TEST,""""""( 1 OR 2 ) AND 3 OR ( 4 OR 5 OR 6 OR 7 )"""""",TEST_CLAUSE,TEST @Value(SECTEUR_1) = MED
      TEST @Value(SECTEUR_1) = MED + PSY
      TEST @Value(LEGENDE) = Postes de garde médecine
      TEST @Value(LEGENDE) = médecine globale et intégrée
      TEST @Value(LEGENDE) = médecine globale et intégrée + consultations psy
      TEST @Value(LEGENDE) = médecine globale et intégrée + planning familial + service de santé mentale
      TEST @Value(LEGENDE) = médecine globale et intégrée + service de santé mentale",maisons médicales + apparentés + postes de garde
    maisons médicales + apparentés + postes de garde -> maisons médicales + apparentés + postes de garde (writer SHAPEFILE_71)
maisons médicales + apparentés + postes de garde (writer SHAPEFILE_71)
    attributes: PERIMETRE number(11,0), ID_FICHE double, LIEN varchar(254), LEGENDE varchar(254), NOM varchar(254), AUTRE_NOM varchar(254), SERV_INT varchar(254), RUE varchar(254), NUMERO double, BOITE double, CP double, COMMUNE varchar(254), REM_ADR varchar(254), QUARTIER varchar(254), QUARTIER_C double, SECT_STAT varchar(254), SECT_STAT_ varchar(254), SITE varchar(254), AUTRE_SITE varchar(254), SITE_AS varchar(254), ZONE_ACTIO varchar(254), LANGUE varchar(254), INTERPRET varchar(254), TYPE varchar(254), QUAND varchar(254), REVUE varchar(254), AGREMENT varchar(254), AUTRES_AGR varchar(254), STATUT_JUR varchar(254), NUM_ENTREP double,
      PUB_MONITE varchar(254), STATUT_LIN varchar(254), ANCIEN_NOM varchar(254), CREE_PAR varchar(254), FAIT_PARTI varchar(254), ANTENNE_DE varchar(254), ORGANISATI varchar(254), SECTEUR varchar(254), MAJ date, ADRESSE varchar(254), SECTEUR_1 varchar(50), ID number(11,0), NAME_FRE varchar(60), SECTEUR_2 varchar(10)
TestFilter_22
    DEFAULT_VALUE = <UNFILTERED>
    TEST_LIST:
      "BOOL_OP,COMPOSITE,COMPOSITE_TEST,""""""( 1 OR 2 ) AND ( 3 OR 4 OR 5 )"""""",TEST_CLAUSE,TEST @Value(SECTEUR_1) = MED
      TEST @Value(SECTEUR_1) = MED + PSY
      TEST @Value(LEGENDE) = médecine globale et intégrée + planning familial + service de santé mentale
      TEST @Value(LEGENDE) = planning familial  + consultations psy
      TEST @Value(LEGENDE) = hôpitaux psy + consultations psy",centre de planning familial
    centre de planning familial -> centre de planning familial (writer SHAPEFILE_81)
centre de planning familial (writer SHAPEFILE_81)
    attributes: PERIMETRE number(11,0), ID_FICHE double, LIEN varchar(254), LEGENDE varchar(254), NOM varchar(254), AUTRE_NOM varchar(254), SERV_INT varchar(254), RUE varchar(254), NUMERO double, BOITE double, CP double, COMMUNE varchar(254), REM_ADR varchar(254), QUARTIER varchar(254), QUARTIER_C double, SECT_STAT varchar(254), SECT_STAT_ varchar(254), SITE varchar(254), AUTRE_SITE varchar(254), SITE_AS varchar(254), ZONE_ACTIO varchar(254), LANGUE varchar(254), INTERPRET varchar(254), TYPE varchar(254), QUAND varchar(254), REVUE varchar(254), AGREMENT varchar(254), AUTRES_AGR varchar(254), STATUT_JUR varchar(254), NUM_ENTREP double,
      PUB_MONITE varchar(254), STATUT_LIN varchar(254), ANCIEN_NOM varchar(254), CREE_PAR varchar(254), FAIT_PARTI varchar(254), ANTENNE_DE varchar(254), ORGANISATI varchar(254), SECTEUR varchar(254), MAJ date, ADRESSE varchar(254), SECTEUR_1 varchar(50), ID number(11,0), NAME_FRE varchar(60), SECTEUR_2 varchar(10)

Bookmark: 02 Equipments culturels
Note: Query: / - FR: "langue" = 'FR' OR "langue" = 'FR, NL' / - NL: "langue" = 'NL' OR "langue" = 'FR, NL'
centres_culturels (reader SHAPEFILE_13)
    attributes: name varchar(254), category varchar(254), website varchar(254), city varchar(254), street_nam varchar(254), street_num varchar(254), address varchar(254), owner_name varchar(254), number_of_ number(11,0), Subs_c_f_n varchar(254), PERIMETRE number(11,0), ID number(11,0), langue varchar(10)
    -> TestFilter_15
    -> TestFilter_16
TestFilter_15
    DEFAULT_VALUE = <UNFILTERED>
    TEST_LIST:
      "BOOL_OP,OR,COMPOSITE_TEST,""""""1 OR 2"""""",TEST_CLAUSE,TEST @Value(langue) = FR
      TEST @Value(langue) = FR, NL",FR
    FR -> FR (writer SHAPEFILE_74)
FR (writer SHAPEFILE_74)
    attributes: name varchar(254), category varchar(254), website varchar(254), city varchar(254), street_nam varchar(254), street_num varchar(254), address varchar(254), owner_name varchar(254), number_of_ number(11,0), Subs_c_f_n varchar(254), PERIMETRE number(11,0), ID number(11,0), langue varchar(10)
TestFilter_16
    DEFAULT_VALUE = <UNFILTERED>
    TEST_LIST:
      "BOOL_OP,OR,COMPOSITE_TEST,""""""1 OR 2"""""",TEST_CLAUSE,TEST @Value(langue) = NL
      TEST @Value(langue) = FR, NL",NL
    NL -> NL (writer SHAPEFILE_75)
NL (writer SHAPEFILE_75)
    attributes: name varchar(254), category varchar(254), website varchar(254), city varchar(254), street_nam varchar(254), street_num varchar(254), address varchar(254), owner_name varchar(254), number_of_ number(11,0), Subs_c_f_n varchar(254), PERIMETRE number(11,0), ID number(11,0), langue varchar(10)

Bookmark: 07 Seniors
Note: Query: / "LEGENDE" LIKE '%Maisons de repos' OR "LEGENDE" LIKE '%résidences-services%'
seniors (reader SHAPEFILE_15)
    attributes: ID_FICHE double, LIEN varchar(254), NOM varchar(254), AUTRE_NOM varchar(254), SERV_INT varchar(254), RUE varchar(254), NUMERO varchar(254), BOITE varchar(254), CP double, COMMUNE varchar(254), REM_ADR varchar(254), QUARTIER varchar(254), QUARTIER_C double, SECT_STAT varchar(254), SECT_STAT_ varchar(254), SITE varchar(254), AUTRE_SITE varchar(254), SITE_AS varchar(254), BENEFICIAI varchar(254), ZONE_ACTIO varchar(254), LANGUE varchar(254), INTERPRET varchar(254), TYPE varchar(254), QUAND varchar(254), REVUE varchar(254), AGREMENT varchar(254), AUTRES_AGR varchar(254), STATUT_JUR varchar(254), NUM_ENTREP double, PUB_MONITE varchar(254),
      STATUT_LIN varchar(254), ANCIEN_NOM varchar(254), FAIT_PARTI varchar(254), ANTENNE_DE varchar(254), ORGANISATI varchar(254), SECTEUR varchar(254), CATEGORIES varchar(254), MAJ date, XCOORD double, YCOORD double, LATITUDE double, LONGITUDE double, LEGENDE varchar(254), ADRESSE varchar(254), PERIMETRE long
    -> TestFilter_19
TestFilter_19
    DEFAULT_VALUE = <UNFILTERED>
    TEST_LIST:
      "BOOL_OP,OR,COMPOSITE_TEST,""""""1 OR 2 OR 3"""""",TEST_CLAUSE,CASE_INSENSITIVE_TEST @Value(LEGENDE) LIKE %Maisons de repos%
      CASE_INSENSITIVE_TEST @Value(LEGENDE) LIKE %MRS%
      CASE_INSENSITIVE_TEST @Value(LEGENDE) LIKE %résidences-services%",maisons de repos + résidences services
    maisons de repos + résidences services -> seniors (writer SHAPEFILE_80)
seniors (writer SHAPEFILE_80)
    attributes: ID_FICHE double, LIEN varchar(254), NOM varchar(254), AUTRE_NOM varchar(254), SERV_INT varchar(254), RUE varchar(254), NUMERO varchar(254), BOITE varchar(254), CP double, COMMUNE varchar(254), REM_ADR varchar(254), QUARTIER varchar(254), QUARTIER_C double, SECT_STAT varchar(254), SECT_STAT_ varchar(254), SITE varchar(254), AUTRE_SITE varchar(254), SITE_AS varchar(254), BENEFICIAI varchar(254), ZONE_ACTIO varchar(254), LANGUE varchar(254), INTERPRET varchar(254), TYPE varchar(254), QUAND varchar(254), REVUE varchar(254), AGREMENT varchar(254), AUTRES_AGR varchar(254), STATUT_JUR varchar(254), NUM_ENTREP double, PUB_MONITE varchar(254),
      STATUT_LIN varchar(254), ANCIEN_NOM varchar(254), FAIT_PARTI varchar(254), ANTENNE_DE varchar(254), ORGANISATI varchar(254), SECTEUR varchar(254), CATEGORIES varchar(254), MAJ date, XCOORD double, YCOORD double, LATITUDE double, LONGITUDE double, LEGENDE varchar(254), ADRESSE varchar(254), PERIMETRE long

Bookmark: 05 ENVIRONNEMENT
Note: Remove Recypark / - Auderghem / - Woluwe Saint Pierre
recypark (reader SHAPEFILE_11)
    attributes: Id long, NOM_FR varchar(100), NOM_NL varchar(100), ADRESSE varchar(240), ADRESS varchar(240), URL_PDF_FR varchar(240), URL_PDF_NL varchar(240), SPECLOC_FR varchar(200), SPECLOC_NL varchar(200), VEHI_OK_FR varchar(100), VEHI_OK_NL varchar(100), TARIF_FR varchar(100), TARIF_NL varchar(100), TYPE varchar(50), VBX_AUTORI varchar(10)
    -> TestFilter_13
TestFilter_13
    DEFAULT_VALUE = <UNFILTERED>
    TEST_LIST = "BOOL_OP,OR,COMPOSITE_TEST,""""""1"""""",TEST_CLAUSE,TEST @Value(VBX_AUTORI) = Oui",Autorisé
    Autorisé -> Recypark autorisé (writer SHAPEFILE_72)
Recypark autorisé (writer SHAPEFILE_72)
    attributes: Id long, NOM_FR varchar(100), NOM_NL varchar(100), ADRESSE varchar(240), ADRESS varchar(240), URL_PDF_FR varchar(240), URL_PDF_NL varchar(240), SPECLOC_FR varchar(200), SPECLOC_NL varchar(200), VEHI_OK_FR varchar(100), VEHI_OK_NL varchar(100), TARIF_FR varchar(100), TARIF_NL varchar(100), TYPE varchar(50), VBX_AUTORI varchar(10)

Bookmark: Commerces
Note: Query - part 1 / * Boulangerie-Pâtisserie : "ID_TYPE" = 11201 / * Boucherie-Charcuterie : "ID_TYPE" = 11203 / * Epicerie-Supérette (+ Fruits&Légumes) : "ID_TYPE" = 11101 OR "ID_TYPE" = 11102 OR "ID_TYPE" = 11107 OR "ID_TYPE" = 11108 OR "ID_TYPE" = 11109 OR "ID_TYPE" = 11206 / * Super-/hyper-marché : "ID_TYPE" = 11103 OR "ID_TYPE" = 11104 / * Pharmacie : "ID_TYPE" = 11405 / * Laverie : "ID_TYPE" = 42101 / * Mutuelle : "ID_TYPE" = 41201 / * Café-ExpressoBar :"ID_TYPE" = 21101 / Query - part 2 / "SECT" = 'Activités sportives'
HUB_POS_OCT_2020_RBC (reader SHAPEFILE_3)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double
    -> TestFilter_5
TestFilter_5
    DEFAULT_VALUE = <UNFILTERED>
    TEST_LIST:
      "BOOL_OP,OR,COMPOSITE_TEST,""""""1"""""",TEST_CLAUSE,TEST @Value(ID_TYPE1) = 11201",Boulangerie-Pâtisserie,"BOOL_OP,OR,COMPOSITE_TEST,""""""1"""""",TEST_CLAUSE,TEST @Value(ID_TYPE1) = 11203",Boucherie-Charcuterie,"BOOL_OP,OR,COMPOSITE_TEST,""""""1 OR 2 OR 3 OR 4 OR 5 OR 6"""""",TEST_CLAUSE,TEST @Value(ID_TYPE1) = 11101
      TEST @Value(ID_TYPE1) = 11102
      TEST @Value(ID_TYPE1) = 11107
      TEST @Value(ID_TYPE1) = 11108
      TEST @Value(ID_TYPE1) = 11109
      TEST @Value(ID_TYPE1) = 11206",Epicerie-Supérette,"BOOL_OP,OR,COMPOSITE_TEST,""""""1 OR 2"""""",TEST_CLAUSE,TEST @Value(ID_TYPE1) = 11103
      TEST @Value(ID_TYPE1) = 11104",Super-/hyper-marché,"BOOL_OP,OR,COMPOSITE_TEST,""""""1"""""",TEST_CLAUSE,TEST @Value(ID_TYPE1) = 11405",Pharmacie,"BOOL_OP,OR,COMPOSITE_TEST,""""""1"""""",TEST_CLAUSE,TEST @Value(ID_TYPE1) = 42101",Laverie,"BOOL_OP,OR,COMPOSITE_TEST,""""""1"""""",TEST_CLAUSE,TEST @Value(ID_TYPE1) = 41201",Mutuelle,"BOOL_OP,OR,COMPOSITE_TEST,""""""1"""""",TEST_CLAUSE,TEST @Value(ID_TYPE1) = 21101",Café-ExpressoBar,"BOOL_OP,OR,COMPOSITE_TEST,""""""1"""""",TEST_CLAUSE,TEST @Value(SECT) = Activités sportives",Activités sportives
    Boulangerie-Pâtisserie -> Boulangerie-Pâtisserie (writer SHAPEFILE_38)
    Boucherie-Charcuterie -> Boucherie-Charcuterie (writer SHAPEFILE_39)
    Epicerie-Supérette -> Epicerie-Supérette (writer SHAPEFILE_40)
    Super-/hyper-marché -> Super-hyper-marché (writer SHAPEFILE_41)
    Pharmacie -> Pharmacie (writer SHAPEFILE_42)
    Laverie -> Laverie (writer SHAPEFILE_43)
    Mutuelle -> Mutuelle (writer SHAPEFILE_44)
    Café-ExpressoBar -> Café-Expressobar (writer SHAPEFILE_45)
    Activités sportives -> Activités sportives (writer SHAPEFILE_70)
Boulangerie-Pâtisserie (writer SHAPEFILE_38)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double
Boucherie-Charcuterie (writer SHAPEFILE_39)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double
Epicerie-Supérette (writer SHAPEFILE_40)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double
Super-hyper-marché (writer SHAPEFILE_41)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double
Pharmacie (writer SHAPEFILE_42)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double
Laverie (writer SHAPEFILE_43)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double
Mutuelle (writer SHAPEFILE_44)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double
Café-Expressobar (writer SHAPEFILE_45)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double
Activités sportives (writer SHAPEFILE_70)
    attributes: FID_ double, NOM varchar(254), RUE varchar(254), NUM double, CP double, COMM varchar(254), ID_CATEG varchar(254), CATEG varchar(254), ID_SECT varchar(254), SECT varchar(254), ID_TYPE1 double, TYPE varchar(254), ADPTID double, DATE date, NOD varchar(254), NOD_NOM varchar(254), ID_QUART varchar(254), QUART varchar(254), ID_SECT_ST varchar(254), SECT_STAT varchar(254), LAT double, LON double, ADPTX double, ADPTY double

Bookmark: 07 MOBILITE
Note: Suppression TYPE : "Parking vélos riverains" (n=5) / TYPE "CAPTOT" : capacité (nb de vélos) => Box à vélo = 5 vélos / Queries : / - Box à vélos : "TYPE" = 'Casier de Bicyclette / Fietskluis' / - Parking vélos : "TYPE" = 'Parking Vélo Public / Openbare Fietsenstalling'
velopark (reader SHAPEFILE_20)
    attributes: NAME_FRE varchar(60), NAME_DUT varchar(60), SECTEUR_ST varchar(200), QUARTIER varchar(200), ZONE varchar(100), COMMUNE varchar(200), TYPE varchar(200), TOTALCAPAC varchar(200), PUBLICACCE varchar(200), AUDIENCE varchar(200), PRICE varchar(200), COVERED varchar(200), PERIMETRE varchar(200)
    -> Tester
Tester
    BOOL_OP = OR
    COMPOSITE_TEST = 1
    TEST_CLAUSE = TEST @Value(TYPE) = Parking Vélo Riverains / Buurtstalling
    TEST_MODE = TEST
    FAILED -> TestFilter
TestFilter
    DEFAULT_VALUE = <UNFILTERED>
    TEST_LIST = "BOOL_OP,OR,COMPOSITE_TEST,""""""1"""""",TEST_CLAUSE,TEST @Value(TYPE) = Casier de Bicyclette / Fietskluis",Box à vélos,"BOOL_OP,OR,COMPOSITE_TEST,""""""1"""""",TEST_CLAUSE,TEST @Value(TYPE) = Parking Vélo Public / Openbare Fietsenstalling",Parking Vélos
    Box à vélos -> Box à vélos (writer SHAPEFILE_30)
    Parking Vélos -> Parking vélos (writer SHAPEFILE_31)
Box à vélos (writer SHAPEFILE_30)
    attributes: NAME_FRE varchar(60), NAME_DUT varchar(60), SECTEUR_ST varchar(200), QUARTIER varchar(200), ZONE varchar(100), COMMUNE varchar(200), TYPE varchar(200), TOTALCAPAC varchar(200), PUBLICACCE varchar(200), AUDIENCE varchar(200), PRICE varchar(200), COVERED varchar(200), PERIMETRE varchar(200)
Parking vélos (writer SHAPEFILE_31)
    attributes: NAME_FRE varchar(60), NAME_DUT varchar(60), SECTEUR_ST varchar(200), QUARTIER varchar(200), ZONE varchar(100), COMMUNE varchar(200), TYPE varchar(200), TOTALCAPAC varchar(200), PUBLICACCE varchar(200), AUDIENCE varchar(200), PRICE varchar(200), COVERED varchar(200), PERIMETRE varchar(200)
Note: Possibilité de diviser (Bus, Metro, Tram)
ACTU_STOPS (reader SHAPEFILE_16)
    attributes: Variante long, succession long, stop_id varchar(254), descr_fr varchar(254), descr_nl varchar(254), alpha_fr varchar(254), alpha_nl varchar(254), coord_x double, coord_y double, mode varchar(254), numero_lig long, terminus varchar(254)
    -> TestFilter_2
TestFilter_2
    DEFAULT_VALUE = <UNFILTERED>
    TEST_LIST = "BOOL_OP,OR,COMPOSITE_TEST,""""""1"""""",TEST_CLAUSE,TEST @Value(mode) = B",Bus,"BOOL_OP,OR,COMPOSITE_TEST,""""""1"""""",TEST_CLAUSE,TEST @Value(mode) = M",Metro,"BOOL_OP,OR,COMPOSITE_TEST,""""""1"""""",TEST_CLAUSE,TEST @Value(mode) = T",Tram
    Bus -> AttributeManager
    Metro -> STIB_Metro (writer SHAPEFILE_34)
    Tram -> STIB_Tram (writer SHAPEFILE_35)
AttributeManager
    ATTR_TABLE = SET_TO fme_feature_type = Bus
    -> ACTU_STOPS (writer SHAPEFILE_32)
ACTU_STOPS (writer SHAPEFILE_32)
    attributes: Variante long, succession long, stop_id varchar(254), descr_fr varchar(254), descr_nl varchar(254), alpha_fr varchar(254), alpha_nl varchar(254), coord_x double, coord_y double, mode varchar(254), numero_lig long, terminus varchar(254), fme_featur varchar(50)
STIB_Metro (writer SHAPEFILE_34)
    attributes: Variante long, succession long, stop_id varchar(254), descr_fr varchar(254), descr_nl varchar(254), alpha_fr varchar(254), alpha_nl varchar(254), coord_x double, coord_y double, mode varchar(254), numero_lig long, terminus varchar(254), fme_featur varchar(50)
STIB_Tram (writer SHAPEFILE_35)
    attributes: Variante long, succession long, stop_id varchar(254), descr_fr varchar(254), descr_nl varchar(254), alpha_fr varchar(254), alpha_nl varchar(254), coord_x double, coord_y double, mode varchar(254), numero_lig long, terminus varchar(254), fme_featur varchar(50)

Bookmark: Bureau de poste - Point-relais
Note: Query: / "TYPE_FR" <> 'Boite aux lettres'
point_postaux_210127 (reader SHAPEFILE_1)
    attributes: TYPE_FR varchar(254), TYPE_NL varchar(254), POSTALOPER varchar(254), NOM_FR varchar(254), NOM_NL varchar(254), RUE_NL varchar(254), RUE_FR varchar(254), housenr varchar(254), Z_PCDD_FR varchar(30), Z_PCDD_NL varchar(30), Z_PCDD varchar(200), OBJECTID long, ID long, NOM_SECTIO varchar(50), ZONE varchar(50), SECTION varchar(50), VERSIONID long, CAPAKEY varchar(20), X double, Y double, ADRVOISFR varchar(200), ADRVOISNL varchar(200), L72_X varchar(200), L72_Y varchar(200), WGS84_LONG varchar(200), WGS84_LAT varchar(200), WGS84_LALO varchar(200), PERIMETRE varchar(200), COMMUNE_FR varchar(60), SHORT_FRE varchar(3),
      COMMUNE_NL varchar(60), SHORT_DUT varchar(3), COUNTRY varchar(2), AREA double, DATEUPDATE varchar(254)
    -> TestFilter_3
TestFilter_3
    DEFAULT_VALUE = <UNFILTERED>
    TEST_LIST = "BOOL_OP,OR,COMPOSITE_TEST,""""""1"""""",TEST_CLAUSE,TEST @Value(TYPE_FR) != Boite aux lettres",ALL w/o boite aux lettres
    ALL w/o boite aux lettres -> ALL_wo_boite_aux_lettres (writer SHAPEFILE_37)
ALL_wo_boite_aux_lettres (writer SHAPEFILE_37)
    attributes: TYPE_FR varchar(254), TYPE_NL varchar(254), POSTALOPER varchar(254), NOM_FR varchar(254), NOM_NL varchar(254), RUE_NL varchar(254), RUE_FR varchar(254), housenr varchar(254), Z_PCDD_FR varchar(30), Z_PCDD_NL varchar(30), Z_PCDD varchar(200), OBJECTID long, ID long, NOM_SECTIO varchar(50), ZONE varchar(50), SECTION varchar(50), VERSIONID long, CAPAKEY varchar(20), X double, Y double, ADRVOISFR varchar(200), ADRVOISNL varchar(200), L72_X varchar(200), L72_Y varchar(200), WGS84_LONG varchar(200), WGS84_LAT varchar(200), WGS84_LALO varchar(200), PERIMETRE varchar(200), COMMUNE_FR varchar(60), SHORT_FRE varchar(3),
      COMMUNE_NL varchar(60), SHORT_DUT varchar(3), COUNTRY varchar(2), AREA double, DATEUPDATE varchar(254)

Bookmark: Marchés
Note: Query: / "AFFICHER" = 1 AND ("CATEGORIE" = 'marché alimentaire classique' OR "CATEGORIE" = 'marché alimentaire + loisirs et degustation')
marches_pt (reader SHAPEFILE_2)
    attributes: Nom varchar(50),Indexed, Lieu varchar(50), Horaires varchar(100), Produits varchar(200), Naam varchar(50), Plaats varchar(50), Dienstrege varchar(100), Producten varchar(200), AFFICHER long, X double, Y double, PERIMETRE long, ID long, URLPDF varchar(200), Remarques varchar(150), Type varchar(50), FREQUENCE varchar(50), CATEGORIE varchar(100), NB_EMPLACE varchar(10)
    -> TestFilter_4
TestFilter_4
    DEFAULT_VALUE = <UNFILTERED>
    TEST_LIST:
      "BOOL_OP,COMPOSITE,COMPOSITE_TEST,""""""1 AND 2 OR 3"""""",TEST_CLAUSE,TEST @Value(AFFICHER) = 1
      TEST @Value(CATEGORIE) = marché alimentaire classique
      TEST @Value(CATEGORIE) = marché alimentaire + loisirs et degustation",@Value(AFFICHER) = 1
    @Value(AFFICHER) = 1 -> marches_pt (writer SHAPEFILE_36)
marches_pt (writer SHAPEFILE_36)
    attributes: Nom varchar(50),Indexed, Lieu varchar(50), Horaires varchar(100), Produits varchar(200), Naam varchar(50), Plaats varchar(50), Dienstrege varchar(100), Producten varchar(200), AFFICHER long, X double, Y double, PERIMETRE long, ID long, URLPDF varchar(200), Remarques varchar(150), Type varchar(50), FREQUENCE varchar(50), CATEGORIE varchar(100), NB_EMPLACE varchar(10)

Bookmark: Plaine de jeux - part 1
Note: Query: / "type" = 'Plaine de jeux'
plaines_jeux_ibge_modifie (reader SHAPEFILE_4)
    attributes: gid varchar(254), id_airesde varchar(254), nom varchar(254), adresse_tx varchar(254), adresse_zi varchar(254), age varchar(254), leeftijd varchar(254), descriptio varchar(254), descriptie varchar(254), heure_ouve varchar(254), openingsti varchar(254), ev_type varchar(254), type varchar(254), soort varchar(254), commune varchar(254), gemeente varchar(254), MODIF varchar(50), gestion varchar(50), PERIMETRE number(11,0), ID number(11,0)
    -> TestFilter_6
TestFilter_6
    DEFAULT_VALUE = <UNFILTERED>
    TEST_LIST = "BOOL_OP,OR,COMPOSITE_TEST,""""""1"""""",TEST_CLAUSE,TEST @Value(type) = Plaine de jeux",Plaine de jeux
    Plaine de jeux -> Plaines de jeux (writer SHAPEFILE_46)
Plaines de jeux (writer SHAPEFILE_46)
    attributes: gid varchar(254), id_airesde varchar(254), nom varchar(254), adresse_tx varchar(254), adresse_zi varchar(254), age varchar(254), leeftijd varchar(254), descriptio varchar(254), descriptie varchar(254), heure_ouve varchar(254), openingsti varchar(254), ev_type varchar(254), type varchar(254), soort varchar(254), commune varchar(254), gemeente varchar(254), MODIF varchar(50), gestion varchar(50), PERIMETRE number(11,0), ID number(11,0)

Bookmark: 05 Petite enfance
Note: Consultation - Query: / - ONE: "SOURCE" = 'ONE' / - K&G: "SOURCE" = 'K&G'
Note: Creches non communales - Query: / *HALTE D'ACCUEIL / - FR: "ORG" = 'ONE' AND "LG" = 'HALTE_ACCUEIL' / - NL: "ORG" = 'K&G' AND "LG" = 'HALTE_ACCUEIL' / *ACCUEILLANTE / - FR: "ORG" = 'ONE' AND "LG" = 'ACCUEILLANTE' / - NL: "ORG" = 'K&G' AND "LG" = 'ACCUEILLANTE' / *CRECHES + PREGARDIENNAT / - FR: "ORG" = 'ONE' AND ("LG" = 'PREGARDIENNAT' OR "LG" = 'CRECHE') / - NL: "ORG" = 'K&G' AND ("LG" = 'PREGARDIENNAT' OR "LG" = 'CRECHE')
Consultations_enfants (reader SHAPEFILE_6)
    attributes: MATRICULE long, DENOMIN varchar(37), TYPE_CONSU varchar(26), RUE varchar(33), NUMERO varchar(8), BOITEPOSTA short, CP long, LOCALITE varchar(27), PROVINCE varchar(19), TEL varchar(17), SOURCE varchar(20)
    -> TestFilter_8
TestFilter_8
    DEFAULT_VALUE = <UNFILTERED>
    TEST_LIST = "BOOL_OP,OR,COMPOSITE_TEST,""""""1"""""",TEST_CLAUSE,TEST @Value(SOURCE) = ONE",ONE,"BOOL_OP,OR,COMPOSITE_TEST,""""""1"""""",TEST_CLAUSE,TEST @Value(SOURCE) = K&G",K&G
    ONE -> ONE (writer SHAPEFILE_49)
    K&G -> K_G (writer SHAPEFILE_50)
ONE (writer SHAPEFILE_49)
    attributes: MATRICULE long, DENOMIN varchar(37), TYPE_CONSU varchar(26), RUE varchar(33), NUMERO varchar(8), BOITEPOSTA short, CP long, LOCALITE varchar(27), PROVINCE varchar(19), TEL varchar(17), SOURCE varchar(20)
K_G (writer SHAPEFILE_50)
    attributes: MATRICULE long, DENOMIN varchar(37), TYPE_CONSU varchar(26), RUE varchar(33), NUMERO varchar(8), BOITEPOSTA short, CP long, LOCALITE varchar(27), PROVINCE varchar(19), TEL varchar(17), SOURCE varchar(20)
creches_non_communales (reader SHAPEFILE_7)
    attributes: NOM varchar(254), ADRESSE varchar(254), CP number(31,15), LANGUE varchar(254), SUBVENTION varchar(254), ORG varchar(254), TYPE varchar(254), LG varchar(254), TERRITOIRE varchar(10), PERIMETRE number(11,0), ID number(11,0), N_PLACES long
    -> TestFilter_12
TestFilter_12
    DEFAULT_VALUE = <UNFILTERED>
    TEST_LIST:
      "BOOL_OP,AND,COMPOSITE_TEST,""""""1 AND 2"""""",TEST_CLAUSE,TEST @Value(ORG) = ONE
      TEST @Value(LG) = HALTE_ACCUEIL",FR_halte d'accueil,"BOOL_OP,AND,COMPOSITE_TEST,""""""1 AND 2"""""",TEST_CLAUSE,TEST @Value(ORG) = K&G
      TEST @Value(LG) = HALTE_ACCUEIL",NL_halte d'accueil,"BOOL_OP,AND,COMPOSITE_TEST,""""""1 AND 2"""""",TEST_CLAUSE,TEST @Value(ORG) = ONE
      TEST @Value(LG) = ACCUEILLANTE",FR_accueillante,"BOOL_OP,AND,COMPOSITE_TEST,""""""1 AND 2"""""",TEST_CLAUSE,TEST @Value(ORG) = K&G
      TEST @Value(LG) = ACCUEILLANTE",NL_accueillante,"BOOL_OP,COMPOSITE,COMPOSITE_TEST,""""""1 AND ( 2 OR 3 )"""""",TEST_CLAUSE,TEST @Value(ORG) = ONE
      TEST @Value(LG) = PREGARDIENNAT
      TEST @Value(LG) = CRECHE",FR_creche_pregardiennat,"BOOL_OP,COMPOSITE,COMPOSITE_TEST,""""""1 AND ( 2 OR 3 )"""""",TEST_CLAUSE,TEST @Value(ORG) = K&G
      TEST @Value(LG) = PREGARDIENNAT
      TEST @Value(LG) = CRECHE",NL_creche_prehardiennat
    FR_halte d'accueil -> FR_halte d'accueil (writer SHAPEFILE_60)
    NL_halte d'accueil -> NL_halte d'accueil (writer SHAPEFILE_61)
    FR_accueillante -> FR_accueillante (writer SHAPEFILE_62)
    NL_accueillante -> NL_accueillante (writer SHAPEFILE_63)
    FR_creche_pregardiennat -> FR_creche_pregardiennat (writer SHAPEFILE_64)
    NL_creche_prehardiennat -> NL_creche_pregardiennat (writer SHAPEFILE_65)
FR_halte d'accueil (writer SHAPEFILE_60)
    attributes: NOM varchar(254), ADRESSE varchar(254), CP number(31,15), LANGUE varchar(254), SUBVENTION varchar(254), ORG varchar(254), TYPE varchar(254), LG varchar(254), TERRITOIRE varchar(10), PERIMETRE number(11,0), ID number(11,0), N_PLACES long
NL_halte d'accueil (writer SHAPEFILE_61)
    attributes: NOM varchar(254), ADRESSE varchar(254), CP number(31,15), LANGUE varchar(254), SUBVENTION varchar(254), ORG varchar(254), TYPE varchar(254), LG varchar(254), TERRITOIRE varchar(10), PERIMETRE number(11,0), ID number(11,0), N_PLACES long
FR_accueillante (writer SHAPEFILE_62)
    attributes: NOM varchar(254), ADRESSE varchar(254), CP number(31,15), LANGUE varchar(254), SUBVENTION varchar(254), ORG varchar(254), TYPE varchar(254), LG varchar(254), TERRITOIRE varchar(10), PERIMETRE number(11,0), ID number(11,0), N_PLACES long
NL_accueillante (writer SHAPEFILE_63)
    attributes: NOM varchar(254), ADRESSE varchar(254), CP number(31,15), LANGUE varchar(254), SUBVENTION varchar(254), ORG varchar(254), TYPE varchar(254), LG varchar(254), TERRITOIRE varchar(10), PERIMETRE number(11,0), ID number(11,0), N_PLACES long
FR_creche_pregardiennat (writer SHAPEFILE_64)
    attributes: NOM varchar(254), ADRESSE varchar(254), CP number(31,15), LANGUE varchar(254), SUBVENTION varchar(254), ORG varchar(254), TYPE varchar(254), LG varchar(254), TERRITOIRE varchar(10), PERIMETRE number(11,0), ID number(11,0), N_PLACES long
NL_creche_pregardiennat (writer SHAPEFILE_65)
    attributes: NOM varchar(254), ADRESSE varchar(254), CP number(31,15), LANGUE varchar(254), SUBVENTION varchar(254), ORG varchar(254), TYPE varchar(254), LG varchar(254), TERRITOIRE varchar(10), PERIMETRE number(11,0), ID number(11,0), N_PLACES long
CrechesCommunales (reader SHAPEFILE_8)
    attributes: Subs_ varchar(254), Age varchar(254), Leeftijd varchar(254), Age_1 varchar(254), Wijk_Quart varchar(254), Adr varchar(254), CP long, Commune varchar(254), Gemeente varchar(254), Municipali varchar(254), Heures_d varchar(254), Openingsti varchar(254), Opening_ho varchar(254), TYPE varchar(50), SECTEUR varchar(50), LG long, Remarques varchar(150), NOMS_USUEL varchar(254), NOMS_OFFIC varchar(254), ID long, NB_PLACES long, NB_EMPLOYE long
    -> TestFilter_11
    -> Halte_d_accueil
    -> Accueillante
    -> Creche
TestFilter_11
    DEFAULT_VALUE = <UNFILTERED>
    TEST_LIST:
      "BOOL_OP,AND,COMPOSITE_TEST,""""""1 AND 2"""""",TEST_CLAUSE,TEST @Value(Subs_) = ONE
      TEST @Value(LG) = 3",FR_halte d'accueil,"BOOL_OP,AND,COMPOSITE_TEST,""""""1 AND 2"""""",TEST_CLAUSE,TEST @Value(Subs_) = K&G
      TEST @Value(LG) = 3",NL_halte d'accueil,"BOOL_OP,AND,COMPOSITE_TEST,""""""1 AND 2"""""",TEST_CLAUSE,TEST @Value(Subs_) = ONE
      TEST @Value(LG) = 2",FR_accueillante,"BOOL_OP,AND,COMPOSITE_TEST,""""""1 AND 2"""""",TEST_CLAUSE,TEST @Value(Subs_) = K&G
      TEST @Value(LG) = 2",NL_accueillante,"BOOL_OP,COMPOSITE,COMPOSITE_TEST,""""""1 AND ( 2 OR 3 )"""""",TEST_CLAUSE,TEST @Value(Subs_) = ONE
      TEST @Value(LG) = 4
      TEST @Value(LG) = 1",FR_creche + pregardiennat,"BOOL_OP,COMPOSITE,COMPOSITE_TEST,""""""1 AND ( 2 OR 3 )"""""",TEST_CLAUSE,TEST @Value(Subs_) = K&G
      TEST @Value(LG) = 4
      TEST @Value(LG) = 1",NL_creche + pregardiennat
    FR_halte d'accueil -> FR_halte d'accueil (writer SHAPEFILE_58)
    NL_halte d'accueil -> NL_halte d'accueil (writer SHAPEFILE_59)
    FR_accueillante -> FR_accueillante (writer SHAPEFILE_66)
    NL_accueillante -> NL_accueillante (writer SHAPEFILE_67)
    FR_creche + pregardiennat -> FR_creche_pregardiennat (writer SHAPEFILE_68)
    NL_creche + pregardiennat -> NL_creche_pregardiennat (writer SHAPEFILE_69)
FR_halte d'accueil (writer SHAPEFILE_58)
    attributes: Subs_ varchar(254), Age varchar(254), Leeftijd varchar(254), Age_1 varchar(254), Wijk_Quart varchar(254), Adr varchar(254), CP long, Commune varchar(254), Gemeente varchar(254), Municipali varchar(254), Heures_d varchar(254), Openingsti varchar(254), Opening_ho varchar(254), TYPE varchar(50), SECTEUR varchar(50), LG long, Remarques varchar(150), NOMS_USUEL varchar(254), NOMS_OFFIC varchar(254), ID long, NB_PLACES long, NB_EMPLOYE long
NL_halte d'accueil (writer SHAPEFILE_59)
    attributes: Subs_ varchar(254), Age varchar(254), Leeftijd varchar(254), Age_1 varchar(254), Wijk_Quart varchar(254), Adr varchar(254), CP long, Commune varchar(254), Gemeente varchar(254), Municipali varchar(254), Heures_d varchar(254), Openingsti varchar(254), Opening_ho varchar(254), TYPE varchar(50), SECTEUR varchar(50), LG long, Remarques varchar(150), NOMS_USUEL varchar(254), NOMS_OFFIC varchar(254), ID long, NB_PLACES long, NB_EMPLOYE long
FR_accueillante (writer SHAPEFILE_66)
    attributes: Subs_ varchar(254), Age varchar(254), Leeftijd varchar(254), Age_1 varchar(254), Wijk_Quart varchar(254), Adr varchar(254), CP long, Commune varchar(254), Gemeente varchar(254), Municipali varchar(254), Heures_d varchar(254), Openingsti varchar(254), Opening_ho varchar(254), TYPE varchar(50), SECTEUR varchar(50), LG long, Remarques varchar(150), NOMS_USUEL varchar(254), NOMS_OFFIC varchar(254), ID long, NB_PLACES long, NB_EMPLOYE long
NL_accueillante (writer SHAPEFILE_67)
    attributes: Subs_ varchar(254), Age varchar(254), Leeftijd varchar(254), Age_1 varchar(254), Wijk_Quart varchar(254), Adr varchar(254), CP long, Commune varchar(254), Gemeente varchar(254), Municipali varchar(254), Heures_d varchar(254), Openingsti varchar(254), Opening_ho varchar(254), TYPE varchar(50), SECTEUR varchar(50), LG long, Remarques varchar(150), NOMS_USUEL varchar(254), NOMS_OFFIC varchar(254), ID long, NB_PLACES long, NB_EMPLOYE long
FR_creche_pregardiennat (writer SHAPEFILE_68)
    attributes: Subs_ varchar(254), Age varchar(254), Leeftijd varchar(254), Age_1 varchar(254), Wijk_Quart varchar(254), Adr varchar(254), CP long, Commune varchar(254), Gemeente varchar(254), Municipali varchar(254), Heures_d varchar(254), Openingsti varchar(254), Opening_ho varchar(254), TYPE varchar(50), SECTEUR varchar(50), LG long, Remarques varchar(150), NOMS_USUEL varchar(254), NOMS_OFFIC varchar(254), ID long, NB_PLACES long, NB_EMPLOYE long
NL_creche_pregardiennat (writer SHAPEFILE_69)
    attributes: Subs_ varchar(254), Age varchar(254), Leeftijd varchar(254), Age_1 varchar(254), Wijk_Quart varchar(254), Adr varchar(254), CP long, Commune varchar(254), Gemeente varchar(254), Municipali varchar(254), Heures_d varchar(254), Openingsti varchar(254), Opening_ho varchar(254), TYPE varchar(50), SECTEUR varchar(50), LG long, Remarques varchar(150), NOMS_USUEL varchar(254), NOMS_OFFIC varchar(254), ID long, NB_PLACES long, NB_EMPLOYE long
Accueillante: TestFilter
    DEFAULT_VALUE = <UNFILTERED>
    TEST_LIST:
      "BOOL_OP,AND,COMPOSITE_TEST,""""""1 AND 2"""""",TEST_CLAUSE,TEST @Value(Subs_) = K&G
      TEST @Value(LG) = 2",NL,"BOOL_OP,AND,COMPOSITE_TEST,""""""1 AND 2"""""",TEST_CLAUSE,TEST @Value(Subs_) = ONE
      TEST @Value(LG) = 2",FR
Note: Creches communales - Query: / *HALTE D'ACCUEIL / - FR: "Subs_" = 'ONE' AND "LG" = 3 / - NL: "Subs_" = 'K&G" AND "LG" = 3 / *ACCUEILLANTE / - FR: "Subs_" = 'ONE' AND "LG" = 2 / - NL: "Subs_" = 'K&G' AND "LG" = 2 / *CRECHES + PREGARDIENNAT / - FR: "Subs_" = 'ONE' AND ("LG" = 4 OR "LG" = 1) / - NL: "Subs_" = 'K&G' AND ("LG" = 4 OR "LG" = 1)
Halte_d_accueil: TestFilter
    DEFAULT_VALUE = <UNFILTERED>
    TEST_LIST:
      "BOOL_OP,AND,COMPOSITE_TEST,""""""1 AND 2"""""",TEST_CLAUSE,TEST @Value(Subs_) = K&G
      TEST @Value(LG) = 3",NL,"BOOL_OP,AND,COMPOSITE_TEST,""""""1 AND 2"""""",TEST_CLAUSE,TEST @Value(Subs_) = ONE
      TEST @Value(LG) = 3",FR
Creche: TestFilter
    DEFAULT_VALUE = <UNFILTERED>
    TEST_LIST:
      "BOOL_OP,COMPOSITE,COMPOSITE_TEST,""""""1 AND ( 2 OR 3 )"""""",TEST_CLAUSE,TEST @Value(Subs_) = K&G
      TEST @Value(LG) = 4
      TEST @Value(LG) = 1",NL,"BOOL_OP,COMPOSITE,COMPOSITE_TEST,""""""1 AND 2 OR 3"""""",TEST_CLAUSE,TEST @Value(Subs_) = ONE
      TEST @Value(LG) = 4
      TEST @Value(LG) = 1",FR

Bookmark: Ludotheques
Note: Query: / - FR: "Specialise" <> 1 AND "LANGUE" = 'FR' / - NL: "Specialise" <-> 1 AND "LANGUE" = 'NL'
Ludotheques (reader SHAPEFILE_5)
    attributes: Nom varchar(254), Adresse varchar(254), CP double, Quartier varchar(254), Source varchar(80), Specialise long, LANGUE varchar(6)
    -> TestFilter_7
TestFilter_7
    DEFAULT_VALUE = <UNFILTERED>
    TEST_LIST:
      "BOOL_OP,AND,COMPOSITE_TEST,""""""1 AND 2"""""",TEST_CLAUSE,TEST @Value(Specialise) != 1
      TEST @Value(LANGUE) = FR",FR,"BOOL_OP,AND,COMPOSITE_TEST,""""""1 AND 2"""""",TEST_CLAUSE,TEST @Value(Specialise) != 1
      TEST @Value(LANGUE) = NL",NL
    FR -> FR (writer SHAPEFILE_47)
    NL -> NL (writer SHAPEFILE_48)
FR (writer SHAPEFILE_47)
    attributes: Nom varchar(254), Adresse varchar(254), CP double, Quartier varchar(254), Source varchar(80), Specialise long, LANGUE varchar(6)
NL (writer SHAPEFILE_48)
    attributes: Nom varchar(254), Adresse varchar(254), CP double, Quartier varchar(254), Source varchar(80), Specialise long, LANGUE varchar(6)

Bookmark: 1. Télécharger et diviser les données
Note: equi_projets: equi_projets [SHAPEFILE] créé avec tous les attributs nécessaires
Note: shapefile est divisé en fonction de l'horizon temporel
equi_projets (reader SHAPEFILE_21)
    attributes: OBJECTID number(11,0), DATE_OUV varchar(50), PU varchar(50), DOSSIER varchar(250), PROGRAMME varchar(250), SERVICE varchar(100), TYPE varchar(50), SUPERFICIE varchar(100), Adresse varchar(50), Quartier varchar(25), Thématique varchar(20), Horizon short, Sous-Thè_1 varchar(50), Capacité long
    -> Shapefile1 (writer SHAPEFILE_93)
Shapefile1 (writer SHAPEFILE_93)
    attributes: OBJECTID number(11,0), DATE_OUV varchar(50), PU varchar(50), DOSSIER varchar(250), PROGRAMME varchar(250), SERVICE varchar(100), TYPE varchar(50), SUPERFICIE varchar(100), Adresse varchar(50), Quartier varchar(25), Thématique varchar(20), Horizon short, Sous_Thè_1 varchar(50), Capacité long
2024 (reader SHAPEFILE_23)
    attributes: OBJECTID number(11,0), DATE_OUV varchar(50), PU varchar(50), DOSSIER varchar(250), PROGRAMME varchar(250), SERVICE varchar(100), TYPE varchar(50), SUPERFICIE varchar(100), Adresse varchar(50), Quartier varchar(25), Thématique varchar(20), Horizon long, Sous_Thè_1 varchar(50), Capacité number(11,0)
    -> Shapefile1 (writer SHAPEFILE_95)
Shapefile1 (writer SHAPEFILE_95)
    attributes: OBJECTID number(11,0), DATE_OUV varchar(50), PU varchar(50), DOSSIER varchar(250), PROGRAMME varchar(250), SERVICE varchar(100), TYPE varchar(50), SUPERFICIE varchar(100), Adresse varchar(50), Quartier varchar(25), Thématique varchar(20), Horizon long, Sous_Thè_1 varchar(50), Capacité number(11,0)
Note: shapefile est divisé en fonction du type de variable
2040 (reader SHAPEFILE_22)
    attributes: OBJECTID number(11,0), DATE_OUV varchar(50), PU varchar(50), DOSSIER varchar(250), PROGRAMME varchar(250), SERVICE varchar(100), TYPE varchar(50), SUPERFICIE varchar(100), Adresse varchar(50), Quartier varchar(25), Thématique varchar(20), Horizon long, Sous_Thè_1 varchar(50), Capacité number(11,0)
    -> Shapefile1 (writer SHAPEFILE_94)
Shapefile1 (writer SHAPEFILE_94)
    attributes: OBJECTID number(11,0), DATE_OUV varchar(50), PU varchar(50), DOSSIER varchar(250), PROGRAMME varchar(250), SERVICE varchar(100), TYPE varchar(50), SUPERFICIE varchar(100), Adresse varchar(50), Quartier varchar(25), Thématique varchar(20), Horizon long, Sous_Thè_1 varchar(50), Capacité number(11,0)

Bookmark: 3. Créer un espace tampon autour des espaces verts et des espaces publics en fonction de la superficie 2024
Espace vert - Macro adapted (reader SHAPEFILE_24)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
    -> Bufferer
Bufferer
    ANGLE = 22.5
    CAP_STYLE = Arc
    CORNER_STYLE = Arc
    MODE = AREA
    OFFSET = @sqrt(@Value(SUPERFICIE)/@pi())
    OFFSET_UNITS = METERS
    PRECISION = APPROX
    BUFFERED -> Espace vert Macro buffer (writer SHAPEFILE_96)
Espace vert Macro buffer (writer SHAPEFILE_96)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
Espace vert - Meso adapted (reader SHAPEFILE_25)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
    -> Bufferer_2
Bufferer_2
    ANGLE = 22.5
    CAP_STYLE = Arc
    CORNER_STYLE = Arc
    MODE = AREA
    OFFSET = @sqrt(@Value(SUPERFICIE)/@pi())
    OFFSET_UNITS = METERS
    PRECISION = APPROX
    BUFFERED -> Espace vert Meso buffer (writer SHAPEFILE_97)
Espace vert Meso buffer (writer SHAPEFILE_97)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
Espace vert - Micro adapted (reader SHAPEFILE_26)
    attributes: OBJECTID number(11,0), DATE_OUV varchar(51), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
    -> Bufferer_3
Bufferer_3
    ANGLE = 22.5
    CAP_STYLE = Arc
    CORNER_STYLE = Arc
    MODE = AREA
    OFFSET = @sqrt(@Value(SUPERFICIE)/@pi())
    OFFSET_UNITS = METERS
    PRECISION = APPROX
    BUFFERED -> Espace vert Micro buffer (writer SHAPEFILE_98)
Espace vert Micro buffer (writer SHAPEFILE_98)
    attributes: OBJECTID number(11,0), DATE_OUV varchar(51), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)

Bookmark: 3. Créer un espace tampon autour des espaces verts et des espaces publics en fonction de la superficie 2040
Espace vert - Macro adapted (reader SHAPEFILE_27)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
    -> Bufferer_4
Bufferer_4
    ANGLE = 22.5
    CAP_STYLE = Arc
    CORNER_STYLE = Arc
    MODE = AREA
    OFFSET = @sqrt(@Value(SUPERFICIE)/@pi())
    OFFSET_UNITS = METERS
    PRECISION = APPROX
    BUFFERED -> Espace vert - Macro buffer (writer SHAPEFILE_99)
Espace vert - Macro buffer (writer SHAPEFILE_99)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
Espace vert Meso adapted (reader SHAPEFILE_28)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
    -> Bufferer_5
Bufferer_5
    ANGLE = 22.5
    CAP_STYLE = Arc
    CORNER_STYLE = Arc
    MODE = AREA
    OFFSET = @sqrt(@Value(SUPERFICIE)/@pi())
    OFFSET_UNITS = METERS
    PRECISION = APPROX
    BUFFERED -> Espace vert - Meso buffer (writer SHAPEFILE_100)
Espace vert - Meso buffer (writer SHAPEFILE_100)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
Espace vert public adapted (reader SHAPEFILE_29)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)
    -> Bufferer_6
Bufferer_6
    ANGLE = 22.5
    CAP_STYLE = Arc
    CORNER_STYLE = Arc
    MODE = AREA
    OFFSET = @sqrt(@Value(SUPERFICIE)/@pi())
    OFFSET_UNITS = METERS
    PRECISION = APPROX
    BUFFERED -> Espace vert public buffer (writer SHAPEFILE_101)
Espace vert public buffer (writer SHAPEFILE_101)
    attributes: OBJECTID number(11,0), DATE_OUV varchar(50), PU varchar(50), DOSSIER varchar(250), PROGRAMME varchar(250), SERVICE varchar(100), TYPE varchar(50), SUPERFICIE varchar(100), Adresse varchar(50), Quartier varchar(25), Thématiqu varchar(20), Horizon number(11,0), Sous_Thè_ varchar(50), Capacité number(11,0)

Bookmark: Soutien scolqire
Note: Query: / "LEGENDE" = 'ecole des devoirs' OR "LEGENDE" = 'ecole des devoirs + médiations scolaire'

Bookmark: Bibliotheques
Note: Query: / - FR: "C_TypeEcol" = 'Bibliothèque' AND "Langue" = 'F' / - NL: "C_TypeEcol" = 'Bibliothèque' AND "Langue" = 'N'

Bookmark: Instruction
Note: Query - part 1 / - FR: "LEGENDE" = 'SAHR' AND "LANGUE" = 'FR' / - NL: "LEGENDE" = 'SAHR' AND "LANGUE" = 'NL' / Query - part 2 / - FR: "TYPE" = 'ordinaire' AND "NIVEAU" = 'maternel' AND "LANGUE" = 'FR' / - NL: "TYPE" = 'ordinaire' AND "NIVEAU" = 'maternel' AND "LANGUE" = 'NL' / Query - part 3 / - FR: "TYPE" = 'ordinaire' AND "NIVEAU" = 'primaire' AND "LANGUE" = 'FR' / - NL: "TYPE" = 'ordinaire' AND "NIVEAU" = 'primaire' AND "LANGUE" = 'NL' / Query - part 4 / - FR: "TYPE" = 'ordinaire' AND "NIVEAU" = 'secondaire' AND "LANGUE" = 'FR' / - NL: "TYPE" = 'ordinaire' AND "NIVEAU" = 'secondaire' AND "LANGUE" = 'NL' / Query - part 5 / "NIVEAU" = 'promotion sociale' OR "NIVEAU" = 'volwasseneonderwijs'

Bookmark: 03 Equipements sportives
Note: Query: / *Hall Omnisport: "omnisport" = 'Oui' / *Terrains de sports spécifiques (indoor ou outdoor) / - Foot: "foot" = 'Oui' / - Tennis: "tennis" = 'Oui' / - Piste d'athlétisme: "athletisme" = 'Oui' / - Hockey: "hockey" = 'Oui' / - Pétanque: "petanque" = 'Oui' / - Rugby: "rugby" = 'Oui' / - Basket: "basket" = 'Oui' / - Badminton: "badminton" = 'Oui' / *Salle sportive polyvalente: "salle_poly" = 'Oui' / *Salle sportive spécifique: / - Art martiaux et boxe: "ArtMarComb" = 'Oui' / - Gymnase: "gymnase" = 'Oui' / - Fitness et musculation: "FitSpinMus" = 'Oui' / - Squash: "squash" = 'Oui' / - Escalade: "escalade" = 'Oui'

Bookmark: 02 Espaces verts
Note: Query: / - Micro qualitatif: "SUBTYPE_2" = 'EV_QUALI' AND "surface" < 1000 / -Meso qualitatif: "SUBTYPE_2" = 'EV_QUALI' AND "surface" >= 1000 AND "surface" < 30000 / -Macro qualitatif: "SUBTYPE_2" = 'EV_QUALI' AND "surface" >= 30000

Bookmark: Plaine de jeux - part 2
Note: Query: / *Terrains de sport + agoraspace: "type" = 'Terrain de sport outdoor' OR "type" = 'Agoraspace' / *Parcours santé + fitness: "type" = 'Parcours santé' OR "type" = 'Fitness' / *Ping pong: "type" = 'Ping Pong' / *Skatepark: "type" = 'Skatepark' / *BMX: "type" = 'BMX' / *Pétanque: "type" = 'Pétanque'

Bookmark: Adaptation des espaces verts - pas des points mais des polygones
Note: Adaptation of attribute table in QGIS / - convert surface area to m2 / - remove units (e.g. 700m2 becomes 700) / - if cell is empty, fill in with 100 for micro, 10000 for meso and 50000 for macro
